FME workspace LUS_V01_ACE_25062026.fmw

Parameters:
- DestDataset_CSV2 = D:\Land\GIS_DATA\Landuse\LanduseSuitability\3_Outputs   # Destination CSV (Comma Separated Value) Folder
- SourceDataset_GEODATABASE_SDE_16 = LandOS   # ArcSDE Geodatabase Connection
- SourceDataset_GEODATABASE_SDE_20 = LandOS   # ArcSDE Geodatabase Connection
- SourceDataset_GEODATABASE_SDE = Contextual   # ArcSDE Geodatabase Connection
- SourceDataset_CSV2_3 = D:\Land\GIS_DATA\Landuse\LanduseSuitability\3_Outputs\LUDB_H3.csv   # Source CSV (Comma Separated Value) File(s)
- SourceDataset_CSV2_6 = D:\Land\GIS_DATA\Landuse\LanduseSuitability\3_Outputs\MeanAnnualRainfall_H3.csv   # Source CSV (Comma Separated Value) File(s)
- SourceDataset_GEODATABASE_SDE_8 = AdminAndCadastral   # ArcSDE Geodatabase Connection
- SourceDataset_CSV2_7 = D:\Land\GIS_DATA\Landuse\LanduseSuitability\3_Outputs\MeanSlope_H3.csv   # Source CSV (Comma Separated Value) File(s)
- SourceDataset_GEODATABASE_SDE_13 = LandOS   # ArcSDE Geodatabase Connection
- SourceDataset_GEODATABASE_SDE_12 = LandOS   # ArcSDE Geodatabase Connection
- SourceDataset_GEODATABASE_SDE_5 = Assets   # ArcSDE Geodatabase Connection
- SourceDataset_CSV2 = D:\Land\GIS_DATA\Landuse\LanduseSuitability\3_Outputs\ClimateVariables_H3.csv   # Source CSV (Comma Separated Value) File(s)
- SourceDataset_NETCDF = I:\Climate\NIWA_Climate_Change_Projections_2024\Individual_Variables\Number_Frost_Days\FD_historical_MMM_CCAM_base_bp1995-2014_MAM_NZ5km.nc   # Source NetCDF File(s)

Readers:
- GEODATABASE_SDE_9: GEODATABASE_SDE from $(SourceDataset_GEODATABASE_SDE_16)
- GEODATABASE_SDE_11: GEODATABASE_SDE from $(SourceDataset_GEODATABASE_SDE_20)
- GEODATABASE_SDE_1: GEODATABASE_SDE from $(SourceDataset_GEODATABASE_SDE)
- CSV2_2: CSV2 from $(SourceDataset_CSV2_3)
- CSV2_5: CSV2 from $(SourceDataset_CSV2_6)
- GEODATABASE_SDE_2: GEODATABASE_SDE from $(SourceDataset_GEODATABASE_SDE_8)
- CSV2_4: CSV2 from $(SourceDataset_CSV2_7)
- GEODATABASE_SDE_4: GEODATABASE_SDE from $(SourceDataset_GEODATABASE_SDE_13)
- GEODATABASE_SDE_6: GEODATABASE_SDE from $(SourceDataset_GEODATABASE_SDE_12)
- GEODATABASE_SDE_3: GEODATABASE_SDE from $(SourceDataset_GEODATABASE_SDE_5)
- CSV2_1: CSV2 from $(SourceDataset_CSV2)
- NETCDF_1: NETCDF from $(SourceDataset_NETCDF)

Writers:
- CSV2_3: CSV2 to $(DestDataset_CSV2)

NETCDF (reader NETCDF_1)
    attributes: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
Note: Python codes for data transformation and RDM analysis are here: hawkes-bay-rc/LandUseSuitability: Codes for building the Land Use Suitability model
CSV (reader CSV2_5)
    attributes: GRID_ID varchar(15), MeanAnnualRainfall uint32
    -> FeatureMerger [SUPPLIER]
FeatureMerger
    ATTR_ACCUM_MODE = Merge Supplier
    ATTR_CONFLICT_RES_LOOKUP = REQUESTOR_IF_CONFLICT
    IGNORE_NULLS = No
    JOIN_KEYS = @Value(GRID_ID) @Value(GRID_ID) AUTO
    MERGE_TYPE_VAL = ATTRIBUTES
    PROCESS_DUPS = NO
    REJECT_NULL_MISSING_KEYS = No
    SUPPLIERS_FIRST = No
    ATTR_CONFLICT_RES = Use Requestor
    MERGE_TYPE = Attributes Only
    MERGED -> FeatureMerger_2 [REQUESTOR]
CSV (reader CSV2_4)
    attributes: GRID_ID varchar(15), MeanSlope real64
    -> FeatureMerger_2 [SUPPLIER]
FeatureMerger_2
    ATTR_ACCUM_MODE = Merge Supplier
    ATTR_CONFLICT_RES_LOOKUP = REQUESTOR_IF_CONFLICT
    IGNORE_NULLS = No
    JOIN_KEYS = @Value(GRID_ID) @Value(GRID_ID) AUTO
    MERGE_TYPE_VAL = ATTRIBUTES
    PROCESS_DUPS = NO
    REJECT_NULL_MISSING_KEYS = No
    SUPPLIERS_FIRST = No
    ATTR_CONFLICT_RES = Use Requestor
    MERGE_TYPE = Attributes Only
    MERGED -> FeatureMerger_3 [REQUESTOR]
CSV (reader CSV2_1)
    attributes: GRID_ID varchar(15), FrostDays_MAM real64, FrostDays_SON real64, GrowingDegreeDays real64, HeatStress_DJF real64, MeanTemp_SON real64, MinTemp_SON real64, MaxTemp_SON real64, MaxTemp_DJF real64, HarvestRainfall_DJF real64
    -> FeatureMerger_3 [SUPPLIER]
FeatureMerger_3
    ATTR_ACCUM_MODE = Merge Supplier
    ATTR_CONFLICT_RES_LOOKUP = REQUESTOR_IF_CONFLICT
    IGNORE_NULLS = No
    JOIN_KEYS = @Value(GRID_ID) @Value(GRID_ID) AUTO
    MERGE_TYPE_VAL = ATTRIBUTES
    PROCESS_DUPS = NO
    REJECT_NULL_MISSING_KEYS = No
    SUPPLIERS_FIRST = No
    ATTR_CONFLICT_RES = Use Requestor
    MERGE_TYPE = Attributes Only
    MERGED -> SpatialRelator [Requestor]
HawkesBay_SMap (reader GEODATABASE_SDE_6)
    attributes: OBJECTID integer, SMU char(254), SMU1 char(28), SMU1_Smapname char(12), SMU1_SiblingRankOrder double, SMU1_SiblingProportion double, SMU1_SiblingConfidence char(1), SMU1_SiblingFH1 char(5), SMU1_SiblingFH2 char(4), SMU1_SiblingFH3 char(4), SMU1_SiblingFH4 char(4), SMU1_SiblingFH5 char(4), SMU1_SiblingFH6 char(4), SMU1_depthRange char(11), SMU1_rootDepthRange char(11), SMU1_RootBarrier char(33), SMU1_RootBarrierFHNum char(4), SMU1_slowDepthRange char(27), SMU1_clayFH1range char(9), SMU1_clayFH2range char(9), SMU1_clayFH3range char(13), SMU1_clayFH4range char(13), SMU1_clayFH5range char(9), SMU1_clayFH6range char(4), SMU1_sandFH1Range char(11), SMU1_sandFH2Range char(9), SMU1_sandFH3Range char(13), SMU1_sandFH4Range char(13), SMU1_sandFH5Range char(10), SMU1_sandFH6Range char(4),
      SMU1_StoneFH1range char(11), SMU1_StoneFH2range char(13), SMU1_StoneFH3range char(13), SMU1_StoneFH4range char(13), SMU1_StoneFH5range char(9), SMU1_StoneFH6range char(4), SMU1_thickFH1range char(11), SMU1_thickFH2range char(11), SMU1_thickFH3range char(10), SMU1_thickFH4range char(10), SMU1_thickFH5range char(10), SMU1_thickFH6range char(4), SMU1_LongSoilName char(44), SMU1_NZSCDescription char(39), SMU1_NZSC char(4), SMU1_NZSCOrder char(1), SMU1_NZSCGroup char(1), SMU1_NZSCSubGroup char(2), SMU1_FamilyName char(14), SMU1_FamilyCode char(5), SMU1_SiblingNum char(4), SMU1_SoilProfileMaterial char(2), SMU1_RockClassRock char(2), SMU1_RockClassFines char(2), SMU1_ParentMaterialOrigin char(5), SMU1_TextureGroupCode char(1), SMU1_PermeabilityCode char(3), SMU1_SiblingDepthCode char(2), SMU1_SiblingTopsoilStonesCode double, SMU1_SiblingDrainageCode char(2),
      SMU1_SiblingTexture char(4), SMU1_RootBarrierCode char(1), SMU2 char(28), SMU2_Smapname char(12), SMU2_SiblingRankOrder double, SMU2_SiblingProportion double, SMU2_SiblingConfidence char(1), SMU2_SiblingFH1 char(5), SMU2_SiblingFH2 char(4), SMU2_SiblingFH3 char(4), SMU2_SiblingFH4 char(4), SMU2_SiblingFH5 char(4), SMU2_SiblingFH6 char(4), SMU2_depthRange char(11), SMU2_rootDepthRange char(11), SMU2_RootBarrier char(33), SMU2_RootBarrierFHNum double, SMU2_slowDepthRange char(27), SMU2_clayFH1range char(13), SMU2_clayFH2range char(13), SMU2_clayFH3range char(13), SMU2_clayFH4range char(13), SMU2_clayFH5range char(9), SMU2_clayFH6range char(4), SMU2_sandFH1Range char(13), SMU2_sandFH2Range char(13), SMU2_sandFH3Range char(13), SMU2_sandFH4Range char(13), SMU2_sandFH5Range char(10), SMU2_sandFH6Range char(4),
      SMU2_StoneFH1range char(11), SMU2_StoneFH2range char(11), SMU2_StoneFH3range char(13), SMU2_StoneFH4range char(13), SMU2_StoneFH5range char(9), SMU2_StoneFH6range char(4), SMU2_thickFH1range char(11), SMU2_thickFH2range char(11), SMU2_thickFH3range char(10), SMU2_thickFH4range char(10), SMU2_thickFH5range char(10), SMU2_thickFH6range char(4), SMU2_LongSoilName char(43), SMU2_NZSCDescription char(39), SMU2_NZSC char(4), SMU2_NZSCOrder char(1), SMU2_NZSCGroup char(1), SMU2_NZSCSubGroup char(2), SMU2_FamilyName char(13), SMU2_FamilyCode char(5), SMU2_SiblingNum char(20), SMU2_SoilProfileMaterial char(2), SMU2_RockClassRock char(2), SMU2_RockClassFines char(2), SMU2_ParentMaterialOrigin char(5), SMU2_TextureGroupCode char(1), SMU2_PermeabilityCode char(3), SMU2_SiblingDepthCode char(2), SMU2_SiblingTopsoilStonesCode char(20), SMU2_SiblingDrainageCode char(2),
      SMU2_SiblingTexture char(4), SMU2_RootBarrierCode char(1), SMU3 char(28), SMU3_Smapname char(12), SMU3_SiblingRankOrder double, SMU3_SiblingProportion double, SMU3_SiblingConfidence char(1), SMU3_SiblingFH1 char(5), SMU3_SiblingFH2 char(4), SMU3_SiblingFH3 char(4), SMU3_SiblingFH4 char(4), SMU3_SiblingFH5 char(4), SMU3_SiblingFH6 char(4), SMU3_depthRange char(11), SMU3_rootDepthRange char(14), SMU3_RootBarrier char(33), SMU3_RootBarrierFHNum char(4), SMU3_slowDepthRange char(27), SMU3_clayFH1range char(9), SMU3_clayFH2range char(9), SMU3_clayFH3range char(13), SMU3_clayFH4range char(13), SMU3_clayFH5range char(9), SMU3_clayFH6range char(4), SMU3_sandFH1Range char(9), SMU3_sandFH2Range char(9), SMU3_sandFH3Range char(13), SMU3_sandFH4Range char(13), SMU3_sandFH5Range char(9), SMU3_sandFH6Range char(4),
      SMU3_StoneFH1range char(13), SMU3_StoneFH2range char(13), SMU3_StoneFH3range char(13), SMU3_StoneFH4range char(13), SMU3_StoneFH5range char(9), SMU3_StoneFH6range char(4), SMU3_thickFH1range char(10), SMU3_thickFH2range char(10), SMU3_thickFH3range char(10), SMU3_thickFH4range char(10), SMU3_thickFH5range char(10), SMU3_thickFH6range char(4), SMU3_LongSoilName char(43), SMU3_NZSCDescription char(32), SMU3_NZSC char(3), SMU3_NZSCOrder char(1), SMU3_NZSCGroup char(1), SMU3_NZSCSubGroup char(1), SMU3_FamilyName char(11), SMU3_FamilyCode char(5), SMU3_SiblingNum char(4), SMU3_SoilProfileMaterial char(2), SMU3_RockClassRock char(2), SMU3_RockClassFines char(2), SMU3_ParentMaterialOrigin char(5), SMU3_TextureGroupCode char(1), SMU3_PermeabilityCode char(3), SMU3_SiblingDepthCode char(2), SMU3_SiblingTopsoilStonesCode double, SMU3_SiblingDrainageCode char(2),
      SMU3_SiblingTexture char(4), SMU3_RootBarrierCode char(1), SMU4 char(28), SMU4_Smapname char(12), SMU4_SiblingRankOrder double, SMU4_SiblingProportion double, SMU4_SiblingConfidence char(1), SMU4_SiblingFH1 char(4), SMU4_SiblingFH2 char(4), SMU4_SiblingFH3 char(4), SMU4_SiblingFH4 char(4), SMU4_SiblingFH5 char(4), SMU4_SiblingFH6 char(4), SMU4_depthRange char(11), SMU4_rootDepthRange char(11), SMU4_RootBarrier char(33), SMU4_RootBarrierFHNum char(4), SMU4_slowDepthRange char(27), SMU4_clayFH1range char(9), SMU4_clayFH2range char(9), SMU4_clayFH3range char(9), SMU4_clayFH4range char(9), SMU4_clayFH5range char(9), SMU4_clayFH6range char(4), SMU4_sandFH1Range char(9), SMU4_sandFH2Range char(9), SMU4_sandFH3Range char(9), SMU4_sandFH4Range char(9), SMU4_sandFH5Range char(9), SMU4_sandFH6Range char(4),
      SMU4_StoneFH1range char(9), SMU4_StoneFH2range char(9), SMU4_StoneFH3range char(13), SMU4_StoneFH4range char(9), SMU4_StoneFH5range char(9), SMU4_StoneFH6range char(4), SMU4_thickFH1range char(10), SMU4_thickFH2range char(10), SMU4_thickFH3range char(10), SMU4_thickFH4range char(10), SMU4_thickFH5range char(10), SMU4_thickFH6range char(4), SMU4_LongSoilName char(42), SMU4_NZSCDescription char(39), SMU4_NZSC char(4), SMU4_NZSCOrder char(1), SMU4_NZSCGroup char(1), SMU4_NZSCSubGroup char(2), SMU4_FamilyName char(10), SMU4_FamilyCode char(5), SMU4_SiblingNum char(4), SMU4_SoilProfileMaterial char(2), SMU4_RockClassRock char(2), SMU4_RockClassFines char(2), SMU4_ParentMaterialOrigin char(5), SMU4_TextureGroupCode char(1), SMU4_PermeabilityCode char(3), SMU4_SiblingDepthCode char(2), SMU4_SiblingTopsoilStonesCode double, SMU4_SiblingDrainageCode char(2),
      SMU4_SiblingTexture char(4), SMU4_RootBarrierCode char(1), SMU5 char(28), SMU5_Smapname char(12), SMU5_SiblingRankOrder double, SMU5_SiblingProportion double, SMU5_SiblingConfidence char(1), SMU5_SiblingFH1 char(4), SMU5_SiblingFH2 char(3), SMU5_SiblingFH3 char(4), SMU5_SiblingFH4 char(4), SMU5_SiblingFH5 char(4), SMU5_SiblingFH6 char(4), SMU5_depthRange char(10), SMU5_rootDepthRange char(10), SMU5_RootBarrier char(33), SMU5_RootBarrierFHNum double, SMU5_slowDepthRange char(27), SMU5_clayFH1range char(9), SMU5_clayFH2range char(9), SMU5_clayFH3range char(9), SMU5_clayFH4range char(9), SMU5_clayFH5range char(9), SMU5_clayFH6range char(4), SMU5_sandFH1Range char(9), SMU5_sandFH2Range char(9), SMU5_sandFH3Range char(9), SMU5_sandFH4Range char(9), SMU5_sandFH5Range char(9), SMU5_sandFH6Range char(4),
      SMU5_StoneFH1range char(8), SMU5_StoneFH2range char(2), SMU5_StoneFH3range char(9), SMU5_StoneFH4range char(9), SMU5_StoneFH5range char(9), SMU5_StoneFH6range char(4), SMU5_thickFH1range char(10), SMU5_thickFH2range char(10), SMU5_thickFH3range char(10), SMU5_thickFH4range char(10), SMU5_thickFH5range char(10), SMU5_thickFH6range char(4), SMU5_LongSoilName char(40), SMU5_NZSCDescription char(39), SMU5_NZSC char(4), SMU5_NZSCOrder char(1), SMU5_NZSCGroup char(1), SMU5_NZSCSubGroup char(2), SMU5_FamilyName char(8), SMU5_FamilyCode char(5), SMU5_SiblingNum double, SMU5_SoilProfileMaterial char(2), SMU5_RockClassRock char(2), SMU5_RockClassFines char(2), SMU5_ParentMaterialOrigin char(5), SMU5_TextureGroupCode char(1), SMU5_PermeabilityCode char(3), SMU5_SiblingDepthCode char(2), SMU5_SiblingTopsoilStonesCode double, SMU5_SiblingDrainageCode char(2),
      SMU5_SiblingTexture char(4), SMU5_RootBarrierCode char(1), SHAPE.STArea() double, SHAPE.STLength() double
    -> AttributeCreator
Note: Salinity
AttributeCreator
    ATTR_TABLE = SET_TO Salinity (int64) = FME_CONDITIONAL:DEFAULT_VALUE'0'BOOL_OP;OR;COMPOSITE_TEST;1;CASE_INSENSITIVE_TEST @Value(SMU1_NZSCDescription) CONTAINS Saline'1'FME_NUM_CONDITIONS2___
    -> AttributeManager_3
AttributeManager_3
    ATTR_TABLE:
      REMOVE OBJECTID (int32)
      REMOVE SMU1 (varchar(28))
      REMOVE SMU1_Smapname (varchar(12))
      REMOVE SMU1_SiblingRankOrder (real64)
      REMOVE SMU1_SiblingProportion (real64)
      REMOVE SMU1_SiblingConfidence (varchar(1))
      REMOVE SMU1_SiblingFH1 (varchar(5))
      REMOVE SMU1_SiblingFH2 (varchar(4))
      REMOVE SMU1_SiblingFH3 (varchar(4))
      REMOVE SMU1_SiblingFH4 (varchar(4))
      REMOVE SMU1_SiblingFH5 (varchar(4))
      REMOVE SMU1_SiblingFH6 (varchar(4))
      REMOVE SMU1_depthRange (varchar(11))
      RENAME_SET_VALUE SMU1_rootDepthRange > RootDepthRange (varchar(11))
      REMOVE SMU1_RootBarrier (varchar(33))
      REMOVE SMU1_RootBarrierFHNum (varchar(4))
      REMOVE SMU1_slowDepthRange (varchar(27))
      REMOVE SMU1_clayFH1range (varchar(9))
      REMOVE SMU1_clayFH2range (varchar(9))
      REMOVE SMU1_clayFH3range (varchar(13))
      REMOVE SMU1_clayFH4range (varchar(13))
      REMOVE SMU1_clayFH5range (varchar(9))
      REMOVE SMU1_clayFH6range (varchar(4))
      REMOVE SMU1_sandFH1Range (varchar(11))
      REMOVE SMU1_sandFH2Range (varchar(9))
      REMOVE SMU1_sandFH3Range (varchar(13))
      REMOVE SMU1_sandFH4Range (varchar(13))
      REMOVE SMU1_sandFH5Range (varchar(10))
      REMOVE SMU1_sandFH6Range (varchar(4))
      REMOVE SMU1_StoneFH1range (varchar(11))
      REMOVE SMU1_StoneFH2range (varchar(13))
      REMOVE SMU1_StoneFH3range (varchar(13))
      REMOVE SMU1_StoneFH4range (varchar(13))
      REMOVE SMU1_StoneFH5range (varchar(9))
      REMOVE SMU1_StoneFH6range (varchar(4))
      REMOVE SMU1_thickFH1range (varchar(11))
      REMOVE SMU1_thickFH2range (varchar(11))
      REMOVE SMU1_thickFH3range (varchar(10))
      REMOVE SMU1_thickFH4range (varchar(10))
      REMOVE SMU1_thickFH5range (varchar(10))
      REMOVE SMU1_thickFH6range (varchar(4))
      REMOVE SMU1_LongSoilName (varchar(44))
      REMOVE SMU1_NZSCDescription (varchar(39))
      REMOVE SMU1_NZSC (varchar(4))
      REMOVE SMU1_NZSCOrder (varchar(1))
      REMOVE SMU1_NZSCGroup (varchar(1))
      REMOVE SMU1_NZSCSubGroup (varchar(2))
      REMOVE SMU1_FamilyName (varchar(14))
      REMOVE SMU1_FamilyCode (varchar(5))
      REMOVE SMU1_SiblingNum (varchar(4))
      REMOVE SMU1_SoilProfileMaterial (varchar(2))
      REMOVE SMU1_RockClassRock (varchar(2))
      REMOVE SMU1_RockClassFines (varchar(2))
      REMOVE SMU1_ParentMaterialOrigin (varchar(5))
      REMOVE SMU1_TextureGroupCode (varchar(1))
      REMOVE SMU1_PermeabilityCode (varchar(3))
      REMOVE SMU1_SiblingDepthCode (varchar(2))
      RENAME_SET_VALUE SMU1_SiblingTopsoilStonesCode > SiblingTopsoilStonesCode (real64)
      REMOVE SMU1_SiblingDrainageCode (varchar(2))
      REMOVE SMU1_SiblingTexture (varchar(4))
      REMOVE SMU1_RootBarrierCode (varchar(1))
      REMOVE SMU2 (varchar(28))
      REMOVE SMU2_Smapname (varchar(12))
      REMOVE SMU2_SiblingRankOrder (real64)
      REMOVE SMU2_SiblingProportion (real64)
      REMOVE SMU2_SiblingConfidence (varchar(1))
      REMOVE SMU2_SiblingFH1 (varchar(5))
      REMOVE SMU2_SiblingFH2 (varchar(4))
      REMOVE SMU2_SiblingFH3 (varchar(4))
      REMOVE SMU2_SiblingFH4 (varchar(4))
      REMOVE SMU2_SiblingFH5 (varchar(4))
      REMOVE SMU2_SiblingFH6 (varchar(4))
      REMOVE SMU2_depthRange (varchar(11))
      REMOVE SMU2_rootDepthRange (varchar(11))
      REMOVE SMU2_RootBarrier (varchar(33))
      REMOVE SMU2_RootBarrierFHNum (real64)
      REMOVE SMU2_slowDepthRange (varchar(27))
      REMOVE SMU2_clayFH1range (varchar(13))
      REMOVE SMU2_clayFH2range (varchar(13))
      REMOVE SMU2_clayFH3range (varchar(13))
      REMOVE SMU2_clayFH4range (varchar(13))
      REMOVE SMU2_clayFH5range (varchar(9))
      REMOVE SMU2_clayFH6range (varchar(4))
      REMOVE SMU2_sandFH1Range (varchar(13))
      REMOVE SMU2_sandFH2Range (varchar(13))
      REMOVE SMU2_sandFH3Range (varchar(13))
      REMOVE SMU2_sandFH4Range (varchar(13))
      REMOVE SMU2_sandFH5Range (varchar(10))
      REMOVE SMU2_sandFH6Range (varchar(4))
      REMOVE SMU2_StoneFH1range (varchar(11))
      REMOVE SMU2_StoneFH2range (varchar(11))
      REMOVE SMU2_StoneFH3range (varchar(13))
      REMOVE SMU2_StoneFH4range (varchar(13))
      REMOVE SMU2_StoneFH5range (varchar(9))
      REMOVE SMU2_StoneFH6range (varchar(4))
      REMOVE SMU2_thickFH1range (varchar(11))
      REMOVE SMU2_thickFH2range (varchar(11))
      REMOVE SMU2_thickFH3range (varchar(10))
      REMOVE SMU2_thickFH4range (varchar(10))
      REMOVE SMU2_thickFH5range (varchar(10))
      REMOVE SMU2_thickFH6range (varchar(4))
      REMOVE SMU2_LongSoilName (varchar(43))
      REMOVE SMU2_NZSCDescription (varchar(39))
      REMOVE SMU2_NZSC (varchar(4))
      REMOVE SMU2_NZSCOrder (varchar(1))
      REMOVE SMU2_NZSCGroup (varchar(1))
      REMOVE SMU2_NZSCSubGroup (varchar(2))
      REMOVE SMU2_FamilyName (varchar(13))
      REMOVE SMU2_FamilyCode (varchar(5))
      REMOVE SMU2_SiblingNum (varchar(20))
      REMOVE SMU2_SoilProfileMaterial (varchar(2))
      REMOVE SMU2_RockClassRock (varchar(2))
      REMOVE SMU2_RockClassFines (varchar(2))
      REMOVE SMU2_ParentMaterialOrigin (varchar(5))
      REMOVE SMU2_TextureGroupCode (varchar(1))
      REMOVE SMU2_PermeabilityCode (varchar(3))
      REMOVE SMU2_SiblingDepthCode (varchar(2))
      REMOVE SMU2_SiblingTopsoilStonesCode (varchar(20))
      REMOVE SMU2_SiblingDrainageCode (varchar(2))
      REMOVE SMU2_SiblingTexture (varchar(4))
      REMOVE SMU2_RootBarrierCode (varchar(1))
      REMOVE SMU3 (varchar(28))
      REMOVE SMU3_Smapname (varchar(12))
      REMOVE SMU3_SiblingRankOrder (real64)
      REMOVE SMU3_SiblingProportion (real64)
      REMOVE SMU3_SiblingConfidence (varchar(1))
      REMOVE SMU3_SiblingFH1 (varchar(5))
      REMOVE SMU3_SiblingFH2 (varchar(4))
      REMOVE SMU3_SiblingFH3 (varchar(4))
      REMOVE SMU3_SiblingFH4 (varchar(4))
      REMOVE SMU3_SiblingFH5 (varchar(4))
      REMOVE SMU3_SiblingFH6 (varchar(4))
      REMOVE SMU3_depthRange (varchar(11))
      REMOVE SMU3_rootDepthRange (varchar(14))
      REMOVE SMU3_RootBarrier (varchar(33))
      REMOVE SMU3_RootBarrierFHNum (varchar(4))
      REMOVE SMU3_slowDepthRange (varchar(27))
      REMOVE SMU3_clayFH1range (varchar(9))
      REMOVE SMU3_clayFH2range (varchar(9))
      REMOVE SMU3_clayFH3range (varchar(13))
      REMOVE SMU3_clayFH4range (varchar(13))
      REMOVE SMU3_clayFH5range (varchar(9))
      REMOVE SMU3_clayFH6range (varchar(4))
      REMOVE SMU3_sandFH1Range (varchar(9))
      REMOVE SMU3_sandFH2Range (varchar(9))
      REMOVE SMU3_sandFH3Range (varchar(13))
      REMOVE SMU3_sandFH4Range (varchar(13))
      REMOVE SMU3_sandFH5Range (varchar(9))
      REMOVE SMU3_sandFH6Range (varchar(4))
      REMOVE SMU3_StoneFH1range (varchar(13))
      REMOVE SMU3_StoneFH2range (varchar(13))
      REMOVE SMU3_StoneFH3range (varchar(13))
      REMOVE SMU3_StoneFH4range (varchar(13))
      REMOVE SMU3_StoneFH5range (varchar(9))
      REMOVE SMU3_StoneFH6range (varchar(4))
      REMOVE SMU3_thickFH1range (varchar(10))
      REMOVE SMU3_thickFH2range (varchar(10))
      REMOVE SMU3_thickFH3range (varchar(10))
      REMOVE SMU3_thickFH4range (varchar(10))
      REMOVE SMU3_thickFH5range (varchar(10))
      REMOVE SMU3_thickFH6range (varchar(4))
      REMOVE SMU3_LongSoilName (varchar(43))
      REMOVE SMU3_NZSCDescription (varchar(32))
      REMOVE SMU3_NZSC (varchar(3))
      REMOVE SMU3_NZSCOrder (varchar(1))
      REMOVE SMU3_NZSCGroup (varchar(1))
      REMOVE SMU3_NZSCSubGroup (varchar(1))
      REMOVE SMU3_FamilyName (varchar(11))
      REMOVE SMU3_FamilyCode (varchar(5))
      REMOVE SMU3_SiblingNum (varchar(4))
      REMOVE SMU3_SoilProfileMaterial (varchar(2))
      REMOVE SMU3_RockClassRock (varchar(2))
      REMOVE SMU3_RockClassFines (varchar(2))
      REMOVE SMU3_ParentMaterialOrigin (varchar(5))
      REMOVE SMU3_TextureGroupCode (varchar(1))
      REMOVE SMU3_PermeabilityCode (varchar(3))
      REMOVE SMU3_SiblingDepthCode (varchar(2))
      REMOVE SMU3_SiblingTopsoilStonesCode (real64)
      REMOVE SMU3_SiblingDrainageCode (varchar(2))
      REMOVE SMU3_SiblingTexture (varchar(4))
      REMOVE SMU3_RootBarrierCode (varchar(1))
      REMOVE SMU4 (varchar(28))
      REMOVE SMU4_Smapname (varchar(12))
      REMOVE SMU4_SiblingRankOrder (real64)
      REMOVE SMU4_SiblingProportion (real64)
      REMOVE SMU4_SiblingConfidence (varchar(1))
      REMOVE SMU4_SiblingFH1 (varchar(4))
      REMOVE SMU4_SiblingFH2 (varchar(4))
      REMOVE SMU4_SiblingFH3 (varchar(4))
      REMOVE SMU4_SiblingFH4 (varchar(4))
      REMOVE SMU4_SiblingFH5 (varchar(4))
      REMOVE SMU4_SiblingFH6 (varchar(4))
      REMOVE SMU4_depthRange (varchar(11))
      REMOVE SMU4_rootDepthRange (varchar(11))
      REMOVE SMU4_RootBarrier (varchar(33))
      REMOVE SMU4_RootBarrierFHNum (varchar(4))
      REMOVE SMU4_slowDepthRange (varchar(27))
      REMOVE SMU4_clayFH1range (varchar(9))
      REMOVE SMU4_clayFH2range (varchar(9))
      REMOVE SMU4_clayFH3range (varchar(9))
      REMOVE SMU4_clayFH4range (varchar(9))
      REMOVE SMU4_clayFH5range (varchar(9))
      REMOVE SMU4_clayFH6range (varchar(4))
      REMOVE SMU4_sandFH1Range (varchar(9))
      REMOVE SMU4_sandFH2Range (varchar(9))
      REMOVE SMU4_sandFH3Range (varchar(9))
      REMOVE SMU4_sandFH4Range (varchar(9))
      REMOVE SMU4_sandFH5Range (varchar(9))
      REMOVE SMU4_sandFH6Range (varchar(4))
      REMOVE SMU4_StoneFH1range (varchar(9))
      REMOVE SMU4_StoneFH2range (varchar(9))
      REMOVE SMU4_StoneFH3range (varchar(13))
      REMOVE SMU4_StoneFH4range (varchar(9))
      REMOVE SMU4_StoneFH5range (varchar(9))
      REMOVE SMU4_StoneFH6range (varchar(4))
      REMOVE SMU4_thickFH1range (varchar(10))
      REMOVE SMU4_thickFH2range (varchar(10))
      REMOVE SMU4_thickFH3range (varchar(10))
      REMOVE SMU4_thickFH4range (varchar(10))
      REMOVE SMU4_thickFH5range (varchar(10))
      REMOVE SMU4_thickFH6range (varchar(4))
      REMOVE SMU4_LongSoilName (varchar(42))
      REMOVE SMU4_NZSCDescription (varchar(39))
      REMOVE SMU4_NZSC (varchar(4))
      REMOVE SMU4_NZSCOrder (varchar(1))
      REMOVE SMU4_NZSCGroup (varchar(1))
      REMOVE SMU4_NZSCSubGroup (varchar(2))
      REMOVE SMU4_FamilyName (varchar(10))
      REMOVE SMU4_FamilyCode (varchar(5))
      REMOVE SMU4_SiblingNum (varchar(4))
      REMOVE SMU4_SoilProfileMaterial (varchar(2))
      REMOVE SMU4_RockClassRock (varchar(2))
      REMOVE SMU4_RockClassFines (varchar(2))
      REMOVE SMU4_ParentMaterialOrigin (varchar(5))
      REMOVE SMU4_TextureGroupCode (varchar(1))
      REMOVE SMU4_PermeabilityCode (varchar(3))
      REMOVE SMU4_SiblingDepthCode (varchar(2))
      REMOVE SMU4_SiblingTopsoilStonesCode (real64)
      REMOVE SMU4_SiblingDrainageCode (varchar(2))
      REMOVE SMU4_SiblingTexture (varchar(4))
      REMOVE SMU4_RootBarrierCode (varchar(1))
      REMOVE SMU5 (varchar(28))
      REMOVE SMU5_Smapname (varchar(12))
      REMOVE SMU5_SiblingRankOrder (real64)
      REMOVE SMU5_SiblingProportion (real64)
      REMOVE SMU5_SiblingConfidence (varchar(1))
      REMOVE SMU5_SiblingFH1 (varchar(4))
      REMOVE SMU5_SiblingFH2 (varchar(3))
      REMOVE SMU5_SiblingFH3 (varchar(4))
      REMOVE SMU5_SiblingFH4 (varchar(4))
      REMOVE SMU5_SiblingFH5 (varchar(4))
      REMOVE SMU5_SiblingFH6 (varchar(4))
      REMOVE SMU5_depthRange (varchar(10))
      REMOVE SMU5_rootDepthRange (varchar(10))
      REMOVE SMU5_RootBarrier (varchar(33))
      REMOVE SMU5_RootBarrierFHNum (real64)
      REMOVE SMU5_slowDepthRange (varchar(27))
      REMOVE SMU5_clayFH1range (varchar(9))
      REMOVE SMU5_clayFH2range (varchar(9))
      REMOVE SMU5_clayFH3range (varchar(9))
      REMOVE SMU5_clayFH4range (varchar(9))
      REMOVE SMU5_clayFH5range (varchar(9))
      REMOVE SMU5_clayFH6range (varchar(4))
      REMOVE SMU5_sandFH1Range (varchar(9))
      REMOVE SMU5_sandFH2Range (varchar(9))
      REMOVE SMU5_sandFH3Range (varchar(9))
      REMOVE SMU5_sandFH4Range (varchar(9))
      REMOVE SMU5_sandFH5Range (varchar(9))
      REMOVE SMU5_sandFH6Range (varchar(4))
      REMOVE SMU5_StoneFH1range (varchar(8))
      REMOVE SMU5_StoneFH2range (varchar(2))
      REMOVE SMU5_StoneFH3range (varchar(9))
      REMOVE SMU5_StoneFH4range (varchar(9))
      REMOVE SMU5_StoneFH5range (varchar(9))
      REMOVE SMU5_StoneFH6range (varchar(4))
      REMOVE SMU5_thickFH1range (varchar(10))
      REMOVE SMU5_thickFH2range (varchar(10))
      REMOVE SMU5_thickFH3range (varchar(10))
      REMOVE SMU5_thickFH4range (varchar(10))
      REMOVE SMU5_thickFH5range (varchar(10))
      REMOVE SMU5_thickFH6range (varchar(4))
      REMOVE SMU5_LongSoilName (varchar(40))
      REMOVE SMU5_NZSCDescription (varchar(39))
      REMOVE SMU5_NZSC (varchar(4))
      REMOVE SMU5_NZSCOrder (varchar(1))
      REMOVE SMU5_NZSCGroup (varchar(1))
      REMOVE SMU5_NZSCSubGroup (varchar(2))
      REMOVE SMU5_FamilyName (varchar(8))
      REMOVE SMU5_FamilyCode (varchar(5))
      REMOVE SMU5_SiblingNum (real64)
      REMOVE SMU5_SoilProfileMaterial (varchar(2))
      REMOVE SMU5_RockClassRock (varchar(2))
      REMOVE SMU5_RockClassFines (varchar(2))
      REMOVE SMU5_ParentMaterialOrigin (varchar(5))
      REMOVE SMU5_TextureGroupCode (varchar(1))
      REMOVE SMU5_PermeabilityCode (varchar(3))
      REMOVE SMU5_SiblingDepthCode (varchar(2))
      REMOVE SMU5_SiblingTopsoilStonesCode (real64)
      REMOVE SMU5_SiblingDrainageCode (varchar(2))
      REMOVE SMU5_SiblingTexture (varchar(4))
      REMOVE SMU5_RootBarrierCode (varchar(1))
      REMOVE SHAPE.STArea() (real64)
      REMOVE SHAPE.STLength() (real64)
    USER_EXPOSED_ATTRIBUTES = Salinity,OBJECTID,SMU,SMU1,SMU1_Smapname,SMU1_SiblingRankOrder,SMU1_SiblingProportion,SMU1_SiblingConfidence,SMU1_SiblingFH1,SMU1_SiblingFH2,SMU1_SiblingFH3,SMU1_SiblingFH4,SMU1_SiblingFH5,SMU1_SiblingFH6,SMU1_depthRange,SMU1_rootDepthRange,SMU1_RootBarrier,SMU1_RootBarrierFHNum,SMU1_slowDepthRange,SMU1_clayFH1range,SMU1_clayFH2range,SMU1_clayFH3range,SMU1_clayFH4range,SMU1_clayFH5range,SMU1_clayFH6range,SMU1_sandFH1Range,SMU1_sandFH2Range,SMU1_sandFH3Range,SMU1_sandFH4Range,SMU1_sandFH5Range,SMU1_sandFH6Range,SMU1_StoneFH1range,SMU1_StoneFH2range,SMU1_StoneFH3range,SMU1_StoneFH4range,SMU1_StoneFH5range,SMU1_StoneFH6range,SMU1_thickFH1range,SMU1_thickFH2range,SMU1_thickFH3range,SMU1_thickFH4range,SMU1_thickFH5range,SMU1_thickFH6range,SMU1_LongSoilName,SMU1_NZSCDescription,SMU1_NZSC,SMU1_NZSCOrder,SMU1_NZSCGroup,SMU1_NZSCSubGroup,SMU1_FamilyName,SMU1_FamilyCode,SMU1_SiblingNum,SMU1_SoilProfileMaterial,SMU1_RockClassRock,SMU1_RockClassFines,SMU1_ParentMaterialOrigin,SMU1_TextureGroupCode,SMU1_PermeabilityCode,SMU1_SiblingDepthCode,SMU1_SiblingTopsoilStonesCode,SMU1_SiblingDrainageCode,SMU1_SiblingTexture,SMU1_RootBarrierCode,SMU2,SMU2_Smapname,SMU2_SiblingRankOrder,SMU2_SiblingProportion,SMU2_SiblingConfidence,SMU2_SiblingFH1,SMU2_SiblingFH2,SMU2_SiblingFH3,SMU2_SiblingFH4,SMU2_SiblingFH5,SMU2_SiblingFH6,SMU2_depthRange,SMU2_rootDepthRange,SMU2_RootBarrier,SMU2_RootBarrierFHNum,SMU2_slowDepthRange,SMU2_clayFH1range,SMU2_clayFH2range,SMU2_clayFH3range,SMU2_clayFH4range,SMU2_clayFH5range,SMU2_clayFH6range,SMU2_sandFH1Range,SMU2_sandFH2Range,SMU2_sandFH3Range,SMU2_sandFH4Range,SMU2_sandFH5Range,SMU2_sandFH6Range,SMU2_StoneFH1range,SMU2_StoneFH2range,SMU2_StoneFH3range,SMU2_StoneFH4range,SMU2_StoneFH5range,SMU2_StoneFH6range,SMU2_thickFH1range,SMU2_thickFH2range,SMU2_thickFH3range,SMU2_thickFH4range,SMU2_thickFH5range,SMU2_thickFH6range,SMU2_LongSoilName,SMU2_NZSCDescription,SMU2_NZSC,SMU2_NZSCOrder,SMU2_NZSCGroup,SMU2_NZSCSubGroup,SMU2_FamilyName,SMU2_FamilyCode,SMU2_SiblingNum,SMU2_SoilProfileMaterial,SMU2_RockClassRock,SMU2_RockClassFines,SMU2_ParentMaterialOrigin,SMU2_TextureGroupCode,SMU2_PermeabilityCode,SMU2_SiblingDepthCode,SMU2_SiblingTopsoilStonesCode,SMU2_SiblingDrainageCode,SMU2_SiblingTexture,SMU2_RootBarrierCode,SMU3,SMU3_Smapname,SMU3_SiblingRankOrder,SMU3_SiblingProportion,SMU3_SiblingConfidence,SMU3_SiblingFH1,SMU3_SiblingFH2,SMU3_SiblingFH3,SMU3_SiblingFH4,SMU3_SiblingFH5,SMU3_SiblingFH6,SMU3_depthRange,SMU3_rootDepthRange,SMU3_RootBarrier,SMU3_RootBarrierFHNum,SMU3_slowDepthRange,SMU3_clayFH1range,SMU3_clayFH2range,SMU3_clayFH3range,SMU3_clayFH4range,SMU3_clayFH5range,SMU3_clayFH6range,SMU3_sandFH1Range,SMU3_sandFH2Range,SMU3_sandFH3Range,SMU3_sandFH4Range,SMU3_sandFH5Range,SMU3_sandFH6Range,SMU3_StoneFH1range,SMU3_StoneFH2range,SMU3_StoneFH3range,SMU3_StoneFH4range,SMU3_StoneFH5range,SMU3_StoneFH6range,SMU3_thickFH1range,SMU3_thickFH2range,SMU3_thickFH3range,SMU3_thickFH4range,SMU3_thickFH5range,SMU3_thickFH6range,SMU3_LongSoilName,SMU3_NZSCDescription,SMU3_NZSC,SMU3_NZSCOrder,SMU3_NZSCGroup,SMU3_NZSCSubGroup,SMU3_FamilyName,SMU3_FamilyCode,SMU3_SiblingNum,SMU3_SoilProfileMaterial,SMU3_RockClassRock,SMU3_RockClassFines,SMU3_ParentMaterialOrigin,SMU3_TextureGroupCode,SMU3_PermeabilityCode,SMU3_SiblingDepthCode,SMU3_SiblingTopsoilStonesCode,SMU3_SiblingDrainageCode,SMU3_SiblingTexture,SMU3_RootBarrierCode,SMU4,SMU4_Smapname,SMU4_SiblingRankOrder,SMU4_SiblingProportion,SMU4_SiblingConfidence,SMU4_SiblingFH1,SMU4_SiblingFH2,SMU4_SiblingFH3,SMU4_SiblingFH4,SMU4_SiblingFH5,SMU4_SiblingFH6,SMU4_depthRange,SMU4_rootDepthRange,SMU4_RootBarrier,SMU4_RootBarrierFHNum,SMU4_slowDepthRange,SMU4_clayFH1range,SMU4_clayFH2range,SMU4_clayFH3range,SMU4_clayFH4range,SMU4_clayFH5range,SMU4_clayFH6range,SMU4_sandFH1Range,SMU4_sandFH2Range,SMU4_sandFH3Range,SMU4_sandFH4Range,SMU4_sandFH5Range,SMU4_sandFH6Range,SMU4_StoneFH1range,SMU4_StoneFH2range,SMU4_StoneFH3range,SMU4_StoneFH4range,SMU4_StoneFH5range,SMU4_StoneFH6range,SMU4_thickFH1range,SMU4_thickFH2range,SMU4_thickFH3range,SMU4_thickFH4range,SMU4_thickFH5range,SMU4_thickFH6range,SMU4_LongSoilName,SMU4_NZSCDescription,SMU4_NZSC,SMU4_NZSCOrder,SMU4_NZSCGroup,SMU4_NZSCSubGroup,SMU4_FamilyName,SMU4_FamilyCode,SMU4_SiblingNum,SMU4_SoilProfileMaterial,SMU4_RockClassRock,SMU4_RockClassFines,SMU4_ParentMaterialOrigin,SMU4_TextureGroupCode,SMU4_PermeabilityCode,SMU4_SiblingDepthCode,SMU4_SiblingTopsoilStonesCode,SMU4_SiblingDrainageCode,SMU4_SiblingTexture,SMU4_RootBarrierCode,SMU5,SMU5_Smapname,SMU5_SiblingRankOrder,SMU5_SiblingProportion,SMU5_SiblingConfidence,SMU5_SiblingFH1,SMU5_SiblingFH2,SMU5_SiblingFH3,SMU5_SiblingFH4,SMU5_SiblingFH5,SMU5_SiblingFH6,SMU5_depthRange,SMU5_rootDepthRange,SMU5_RootBarrier,SMU5_RootBarrierFHNum,SMU5_slowDepthRange,SMU5_clayFH1range,SMU5_clayFH2range,SMU5_clayFH3range,SMU5_clayFH4range,SMU5_clayFH5range,SMU5_clayFH6range,SMU5_sandFH1Range,SMU5_sandFH2Range,SMU5_sandFH3Range,SMU5_sandFH4Range,SMU5_sandFH5Range,SMU5_sandFH6Range,SMU5_StoneFH1range,SMU5_StoneFH2range,SMU5_StoneFH3range,SMU5_StoneFH4range,SMU5_StoneFH5range,SMU5_StoneFH6range,SMU5_thickFH1range,SMU5_thickFH2range,SMU5_thickFH3range,SMU5_thickFH4range,SMU5_thickFH5range,SMU5_thickFH6range,SMU5_LongSoilName,SMU5_NZSCDescription,SMU5_NZSC,SMU5_NZSCOrder,SMU5_NZSCGroup,SMU5_NZSCSubGroup,SMU5_FamilyName,SMU5_FamilyCode,SMU5_SiblingNum,SMU5_SoilProfileMaterial,SMU5_RockClassRock,SMU5_RockClassFines,SMU5_ParentMaterialOrigin,SMU5_TextureGroupCode,SMU5_PermeabilityCode,SMU5_SiblingDepthCode,SMU5_SiblingTopsoilStonesCode,SMU5_SiblingDrainageCode,SMU5_SiblingTexture,SMU5_RootBarrierCode,SHAPE.STArea(),SHAPE.STLength()
    -> FeatureMerger_5 [REQUESTOR]
zHawkesBay_SMap_SourceSiblingLicensed_April2024 (reader GEODATABASE_SDE_4)
    attributes: OBJECTID integer, SMU char(1073741822), SMU1 char(1073741822), SMU2 char(1073741822), SMU3 char(1073741822), SMU4 char(1073741822), SMU5 char(1073741822), Smapname char(1073741822), SiblingRankOrder integer, SiblingProportion integer, SiblingConfidence char(1073741822), NZSCOrder char(1073741822), SCSHydrologicalSoilGroup char(1073741822), AWmm30 double, AWmm60 double, PAWmm double, WeightAvgPAW_1m double, WeightAvgAWtop80 double, WeightAvgAWtop60 double, WeightAvgAWtop30 double, PRetentionTopsoil integer, ErosionVulnerability char(1073741822), sviClass char(1073741822), sviclassTxt char(1073741822), PuggingRisk char(1073741822), WaterLoggedVulnIrrigated char(1073741822), DroughtVulnerability char(1073741822), RelativeRunoffPotential char(1073741822), RelativeBypassFlow char(1073741822), RelativeNLeachRisk char(1073741822),
      EffluentClass char(1073741822), OverseerParamLevel integer, OVSR_RootDepth double, OVSR_RootDepthText char(1073741822), OVSR_ImpededLayerDepth double, OVSR_ImpededLayerDepthText char(1073741822), DrainageClass char(1073741822), OVSR_TopsoilBulkDensity double, OVSR_TopSoilClay double, OVSR_SubsoilClay integer, OVSR_TopSoilSand double, OVSR_WiltingPointTop integer, OVSR_WiltingPointMiddle integer, OVSR_WiltingPointBottom integer, OVSR_FieldCapacityTop integer, OVSR_FieldCapacityMiddle integer, OVSR_FieldCapacityBottom integer, OVSR_SaturationTop integer, OVSR_SaturationMiddle integer, OVSR_SaturationBottom integer
    -> AttributeManager_5
AttributeManager_5
    ATTR_TABLE:
      REMOVE SMU1 (varchar(1073741822))
      REMOVE SMU2 (varchar(1073741822))
      REMOVE SMU3 (varchar(1073741822))
      REMOVE SMU4 (varchar(1073741822))
      REMOVE SMU5 (varchar(1073741822))
      REMOVE Smapname (varchar(1073741822))
      REMOVE SiblingRankOrder (int32)
      REMOVE SiblingProportion (int32)
      REMOVE SiblingConfidence (varchar(1073741822))
      REMOVE NZSCOrder (varchar(1073741822))
      REMOVE SCSHydrologicalSoilGroup (varchar(1073741822))
      REMOVE AWmm30 (real64)
      REMOVE AWmm60 (real64)
      REMOVE WeightAvgPAW_1m (real64)
      REMOVE WeightAvgAWtop80 (real64)
      REMOVE WeightAvgAWtop60 (real64)
      REMOVE WeightAvgAWtop30 (real64)
      REMOVE PRetentionTopsoil (int32)
      REMOVE ErosionVulnerability (varchar(1073741822))
      REMOVE sviClass (varchar(1073741822))
      REMOVE sviclassTxt (varchar(1073741822))
      REMOVE PuggingRisk (varchar(1073741822))
      REMOVE WaterLoggedVulnIrrigated (varchar(1073741822))
      REMOVE DroughtVulnerability (varchar(1073741822))
      REMOVE RelativeRunoffPotential (varchar(1073741822))
      REMOVE RelativeBypassFlow (varchar(1073741822))
      REMOVE RelativeNLeachRisk (varchar(1073741822))
      REMOVE EffluentClass (varchar(1073741822))
      REMOVE OverseerParamLevel (int32)
      REMOVE OVSR_RootDepth (real64)
      REMOVE OVSR_RootDepthText (varchar(1073741822))
      REMOVE OVSR_ImpededLayerDepth (real64)
      REMOVE OVSR_ImpededLayerDepthText (varchar(1073741822))
      REMOVE OVSR_TopsoilBulkDensity (real64)
      REMOVE OVSR_TopSoilClay (real64)
      REMOVE OVSR_SubsoilClay (int32)
      REMOVE OVSR_TopSoilSand (real64)
      REMOVE OVSR_WiltingPointTop (int32)
      REMOVE OVSR_WiltingPointMiddle (int32)
      REMOVE OVSR_WiltingPointBottom (int32)
      REMOVE OVSR_FieldCapacityTop (int32)
      REMOVE OVSR_FieldCapacityMiddle (int32)
      REMOVE OVSR_FieldCapacityBottom (int32)
      REMOVE OVSR_SaturationTop (int32)
      REMOVE OVSR_SaturationMiddle (int32)
      REMOVE OVSR_SaturationBottom (int32)
    -> FeatureMerger_5 [SUPPLIER]
FeatureMerger_5
    ATTR_ACCUM_MODE = Merge Supplier
    ATTR_CONFLICT_RES_LOOKUP = REQUESTOR_IF_CONFLICT
    IGNORE_NULLS = No
    JOIN_KEYS = @Value(SMU) @Value(SMU) AUTO
    MERGE_TYPE_VAL = ATTRIBUTES
    PROCESS_DUPS = NO
    REJECT_NULL_MISSING_KEYS = No
    SUPPLIERS_FIRST = No
    ATTR_CONFLICT_RES = Use Requestor
    MERGE_TYPE = Attributes Only
    MERGED -> SpatialRelator_2 [Requestor]
HawkesBay_FundamentalSoils (reader GEODATABASE_SDE_11)
    attributes: OBJECTID integer, AREA_ double, PERIMETER double, SIFSL_ integer, SIFSL_ID integer, DOMSOI char(9), SURVEY char(32), SURCODE char(4), MAINSOIL char(8), SOIL char(22), SERIES char(35), SOILTYPE char(46), PHASE char(35), GENSOI char(5), NZSC char(19), DOMNZSC char(4), NZGSOIGRP char(10), SOILLABEL char(27), NZSCLABEL char(19), AREAH double, PH_CLASS char(1), PH_MIN double, PH_MAX double, PH_MID double, PH_VAR char(2), PH_EST char(2), SAL_CLASS char(1), SAL_MIN double, SAL_MAX double, SAL_MID double,
      SAL_VAR char(2), SAL_EST char(2), CEC_CLASS char(1), CEC_MIN double, CEC_MAX double, CEC_MID double, CEC_VAR char(2), CEC_EST char(2), CARBON_CLA char(1), CARBON_MIN double, CARBON_MAX double, CARBON_MID double, CARBON_VAR char(2), CARBON_EST char(2), PRET_CLASS char(1), PRET_MIN smallint, PRET_MAX smallint, PRET_MID smallint, PRET_VAR char(2), PRET_EST char(2), GRAV_CLASS char(1), GRAV_MIN smallint, GRAV_MAX smallint, GRAV_MID smallint, GRAV_VAR char(2), GRAV_EST char(2), ROCK_CLASS char(1), ROCK_MIN smallint, ROCK_MAX smallint, ROCK_MID smallint,
      ROCK_VAR char(2), ROCK_EST char(2), PS char(5), PRD_CLASS char(1), PRD_MIN double, PRD_MAX double, PRD_MID double, PRD_VAR char(2), PRD_EST char(2), DSLO_CLASS char(1), DSLO_MIN double, DSLO_MAX double, DSLO_MID double, DSLO_VAR char(2), DSLO_EST char(2), DRAIN_CLAS char(1), DRAIN_VAR char(2), DRAIN_EST char(2), PERMEABILI char(4), FLOOD_CLAS char(1), FLOOD_VAR char(2), FLOOD_EST char(2), TEMP_CLASS char(2), TEMP_VAR char(2), TEMP_EST char(2), PAW_CLASS char(1), PAW_MIN smallint, PAW_MAX smallint, PAW_MID smallint, PAW_VAR char(2),
      PAW_EST char(2), PRAW_CLASS char(1), PRAW_MIN smallint, PRAW_MAX smallint, PRAW_MID smallint, PRAW_VAR char(2), PRAW_EST char(2), MPOR_S_CLA char(1), MPOR_S_MIN double, MPOR_S_MAX double, MPOR_S_MID double, MPOR_S_VAR char(2), MPOR_S_EST char(2), MPOR_D_CLA char(1), MPOR_D_MIN double, MPOR_D_MAX double, MPOR_D_MID double, MPOR_D_VAR char(2), MPOR_D_EST char(2), EDITION char(3), POLYID integer, Shape.STArea() double, Shape.STLength() double
    -> AttributeKeeper_4
AttributeKeeper_4
    CREATE_BULK_MODE_FEATURES = NO
    KEEP_ATTRS = PH_MID
    -> SpatialRelator_4 [Supplier]
zHawkesBay_SMap_SourceSiblingBaseProperty_Aug2024 (reader GEODATABASE_SDE_4)
    attributes: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
zHawkesBay_SMap_SourceSiblingBasicData_Aug2024 (reader GEODATABASE_SDE_4)
    attributes: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
zHawkesBay_SMap_SourceSiblingLicensed_Aug2024 (reader GEODATABASE_SDE_4)
    attributes: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
HawkesBay_AssetManagement_AssetLines (reader GEODATABASE_SDE_3)
    attributes: AssetType char(50), SHAPE_STLength__ double, SchemeName char(50), Details char(100), AssetMaintenance char(1), CreatedDate date, ModifiedDate date, CreateModifiedBy char(50), GIS_ID integer, GlobalID globalid, Tech1_ID char(25), Maintenance_Responsibility char(25), Asset_Owner char(25), Area_Park char(50), AssetSubType char(50), Material char(50), LastModifiedBy char(50), OBJECTID integer, OldAssetID char(20), River_StreamName char(40), OldAssetID_Chain char(250), SHAPE.STLength() double
    -> Tester
Tester
    BOOL_OP = OR
    TEST_CLAUSE = TEST @Value(AssetType) = Drain
    TEST_MODE = TEST
    PASSED -> SpatialRelator_3 [Supplier]
HawkesBay_DrainageAreas (reader GEODATABASE_SDE_3)
    attributes: OBJECTID integer, DRAINAREA char(40), created_user char(255), created_date date, last_edited_user char(255), last_edited_date date, Shape.STArea() double, Shape.STLength() double
    -> SpatialRelator_2 [Supplier]
SpatialRelator_2
    AGGREGATE_HANDLING = Yes
    CALC_CARD = No
    CURVE_BOUNDARY_RULE_PARAM = Default Rule
    PREDICATES = INTERSECTS
    SUCCESS_ATTR = _related_suppliers
    -> AttributeManager_6
AttributeManager_6
    ATTR_TABLE:
      REMOVE OBJECTID (int32)
      SET_TO DrainageClass (varchar(1073741822)) = FME_CONDITIONAL:DEFAULT_VALUE'_FME_NO_OP_'BOOL_OP;OR;COMPOSITE_TEST;1;TEST @Value(_related_suppliers) > 0'Moderately well drained'FME_NUM_CONDITIONS2___
    -> SpatialRelator_3 [Requestor]
SpatialRelator_3
    AGGREGATE_HANDLING = Yes
    CALC_CARD = No
    CURVE_BOUNDARY_RULE_PARAM = Default Rule
    PREDICATES = INTERSECTS
    SUCCESS_ATTR = _related_suppliers2
    -> AttributeManager_7
AttributeManager_7
    ATTR_TABLE = SET_TO DrainageClass (varchar(1073741822)) = FME_CONDITIONAL:DEFAULT_VALUE'_FME_NO_OP_'BOOL_OP;OR;COMPOSITE_TEST;1;TEST @Value(_related_suppliers2) > 0'Moderately well drained'FME_NUM_CONDITIONS2___
    -> SpatialRelator [Supplier]
SpatialRelator
    AGGREGATE_HANDLING = Yes
    ATTR_ACCUM_MODE = Merge Supplier
    ATTR_CONFLICT_RES = Use Requestor
    CALC_CARD = No
    CURVE_BOUNDARY_RULE_PARAM = Default Rule
    IGNORE_NULLS = Yes
    PREDICATES = INTERSECTS
    SUCCESS_ATTR = _related_suppliers
    -> AttributeManager_2
AttributeManager_2
    ATTR_TABLE:
      REMOVE _related_suppliers (uint32)
      REMOVE _clipped (char(3))
      REMOVE _related_suppliers2 (uint32)
    -> SpatialRelator_4 [Requestor]
SpatialRelator_4
    AGGREGATE_HANDLING = Yes
    ATTR_ACCUM_MODE = Merge Supplier
    ATTR_CONFLICT_RES = Use Requestor
    CALC_CARD = No
    CURVE_BOUNDARY_RULE_PARAM = Default Rule
    IGNORE_NULLS = Yes
    PREDICATES = INTERSECTS
    SUCCESS_ATTR = _related_suppliers
    -> AttributeManager_4
AttributeManager_4
    ATTR_TABLE = REMOVE _related_suppliers (uint32)
    -> CropSuitability (writer CSV2_3)

Bookmark: Input geometry and Grid ID
HawkesBay_Regional_Boundary_2025 (reader GEODATABASE_SDE_2)
    attributes: OBJECTID integer, REGC_V1_00 char(2), REGC_V1_00_NAME char(254), REGC_V1_00_NAME_ASCII char(200), LAND_AREA_SQ_KM double, SHAPE.STArea() double, SHAPE.STLength() double
    -> Clipper [CLIPPER]
HawkesBay_H3Resolution11 (reader GEODATABASE_SDE_1)
    attributes: OBJECTID integer, GRID_ID char(17), SHAPE.STArea() double, SHAPE.STLength() double
    -> AttributeKeeper
AttributeKeeper
    CREATE_BULK_MODE_FEATURES = NO
    KEEP_ATTRS = GRID_ID
    -> Clipper [CANDIDATE]
Clipper
    ADD_NODATA = YES
    BOUNDARY_CASES = INSIDE
    CLEANING_TOLERANCE_LOOKUP = AUTO
    CLIPPED_ATTR = _clipped
    CLIPPERS_FIRST = NO
    GENERATE_LIST = NO
    INVALID_PARTS_HANDLING = REJECT_WHOLE
    MISSING_M_MODE_LOOKUP = LINEAR
    MISSING_Z_MODE_LOOKUP = PLANAR
    MULTIPLE_CLIPPERS = YES
    M_VAL_SOURCE = CANDIDATE
    OVERLAPPING_CLIPPERS = CLIP_OUTSIDE
    PRESERVE_RASTER_EXTENTS = NO
    RASTER_CELL_MODE = CENTER
    Z_VAL_SOURCE = CANDIDATE
    CLEANING_TOLERANCE = Automatic
    MISSING_M_MODE = Linear Interpolation
    MISSING_Z_MODE = Planar Interpolation
    INSIDE -> FeatureMerger_4 [REQUESTOR]

Bookmark: Land use
Note: LUDB 2026 converted using centrepoint in H3Res11 vectortodggs script
CSV (reader CSV2_2)
    attributes: GRID_ID varchar(15), LandUseNam varchar(72), LandUseGro varchar(29)
    -> AttributeManager
AttributeManager
    ATTR_TABLE:
      RENAME_SET_VALUE LandUseNam > LandUseName (varchar(72))
      RENAME_SET_VALUE LandUseGro > LandUseGroup (varchar(29))
    -> FeatureMerger_4 [SUPPLIER]
FeatureMerger_4
    ATTR_ACCUM_MODE = Merge Supplier
    ATTR_CONFLICT_RES_LOOKUP = REQUESTOR_IF_CONFLICT
    IGNORE_NULLS = No
    JOIN_KEYS = @Value(GRID_ID) @Value(GRID_ID) AUTO
    MERGE_TYPE_VAL = ATTRIBUTES
    PROCESS_DUPS = NO
    REJECT_NULL_MISSING_KEYS = No
    SUPPLIERS_FIRST = No
    ATTR_CONFLICT_RES = Use Requestor
    MERGE_TYPE = Attributes Only
    MERGED -> FeatureMerger [REQUESTOR]

Bookmark: Outputs
Note: CSV
CropSuitability (writer CSV2_3)
    attributes: GRID_ID varchar(17), LandUseName varchar(72), LandUseGroup varchar(29), MeanAnnualRainfall uint32, MeanSlope real64, SMU varchar(254), SiblingTopsoilStonesCode string, PAWmm string, RootDepthRange varchar(200), DrainageClass varchar(1073741822), FrostDays_MAM real64, FrostDays_SON real64, GrowingDegreeDays real64, Salinity int64, PH_MID string, HeatStress_DJF real64, MeanTemp_SON real64, MinTemp_SON real64, MaxTemp_SON real64, MaxTemp_DJF real64, HarvestRainfall_DJF real64

Bookmark: Physical parameters - Climate and slope
Note: Mean Annual Rainfall uses rastertodggs.py
Note: Mean Slope uses rastertodggs.py
Note: Climate variables from netcdf. See python code: netcdftodggs.py

Bookmark: Physical parameters - Soils
Note: Drainage
