FME workspace LUS_PostProcessing_V01_ACE_25062026.fmw

Parameters:
- SourceDataset_GEODATABASE_SDE_16 = LandOS   # ArcSDE Geodatabase Connection
- DestDataset_GEODATABASE_FILE = D:\Land\GIS_DATA\Landuse\LanduseSuitability\3_Outputs\LUS_Outputs.gdb   # File Geodatabase
- SourceDataset_GEODATABASE_SDE = Contextual   # ArcSDE Geodatabase Connection
- SourceDataset_GEODATABASE_SDE_10 = AdminAndCadastral   # ArcSDE Geodatabase Connection
- SourceDataset_CSV2_9 = D:\Land\GIS_DATA\Landuse\LanduseSuitability\3_Outputs\LUDB_H3.csv   # Source CSV (Comma Separated Value) File(s)
- SourceDataset_CSV2_7 = D:\Land\GIS_DATA\Landuse\LanduseSuitability\3_Outputs\RTRP_TreeSpecies_H3Res11.csv   # Source CSV (Comma Separated Value) File(s)
- DestDataset_GEODATABASE_FILE_13 = D:\Land\GIS_DATA\Landuse\LanduseSuitability\3_Outputs\LUS_Outputs.gdb   # File Geodatabase
- SourceDataset_GEODATABASE_SDE_7 = LandOS   # ArcSDE Geodatabase Connection
- DestDataset_GEODATABASE_FILE_19 = D:\Land\GIS_DATA\Landuse\LanduseSuitability\3_Outputs\LUS_Outputs.gdb   # File Geodatabase
- SourceDataset_CSV2 = D:\Land\GIS_DATA\Landuse\LanduseSuitability\3_Outputs\CropSuitabilityClassified_ALL.csv   # Source CSV (Comma Separated Value) File(s)
- DestDataset_GEODATABASE_FILE_17 = D:\Land\GIS_DATA\Landuse\LanduseSuitability\3_Outputs\LUS_Outputs.gdb   # File Geodatabase
- DestDataset_GEODATABASE_FILE_15 = D:\Land\GIS_DATA\Landuse\LanduseSuitability\3_Outputs\LUS_Outputs.gdb   # File Geodatabase
- DestDataset_GEODATABASE_FILE_21 = D:\Land\GIS_DATA\Landuse\LanduseSuitability\3_Outputs\LUS_Outputs.gdb   # File Geodatabase
- DestDataset_GEODATABASE_FILE_12 = D:\Land\GIS_DATA\Landuse\LanduseSuitability\3_Outputs\LUS_Outputs.gdb   # File Geodatabase
- DestDataset_GEODATABASE_FILE_14 = D:\Land\GIS_DATA\Landuse\LanduseSuitability\3_Outputs\LUS_Outputs.gdb   # File Geodatabase
- DestDataset_GEODATABASE_FILE_16 = D:\Land\GIS_DATA\Landuse\LanduseSuitability\3_Outputs\LUS_Outputs.gdb   # File Geodatabase
- DestDataset_GEODATABASE_FILE_18 = D:\Land\GIS_DATA\Landuse\LanduseSuitability\3_Outputs\LUS_Outputs.gdb   # File Geodatabase
- DestDataset_GEODATABASE_FILE_20 = D:\Land\GIS_DATA\Landuse\LanduseSuitability\3_Outputs\LUS_Outputs.gdb   # File Geodatabase
- SourceDataset_GEODATABASE_SDE_6 = Coastal   # ArcSDE Geodatabase Connection

Readers:
- GEODATABASE_SDE_9: GEODATABASE_SDE from $(SourceDataset_GEODATABASE_SDE_16)
- GEODATABASE_SDE_1: GEODATABASE_SDE from $(SourceDataset_GEODATABASE_SDE)
- GEODATABASE_SDE_2: GEODATABASE_SDE from $(SourceDataset_GEODATABASE_SDE_10)
- CSV2_2: CSV2 from $(SourceDataset_CSV2_9)
- CSV2_3: CSV2 from $(SourceDataset_CSV2_7)
- GEODATABASE_SDE_3: GEODATABASE_SDE from $(SourceDataset_GEODATABASE_SDE_7)
- CSV2_1: CSV2 from $(SourceDataset_CSV2)
- GEODATABASE_SDE_4: GEODATABASE_SDE from $(SourceDataset_GEODATABASE_SDE_6)

Writers:
- GEODATABASE_FILE_1: GEODATABASE_FILE to $(DestDataset_GEODATABASE_FILE)
- GEODATABASE_FILE_3: GEODATABASE_FILE to $(DestDataset_GEODATABASE_FILE_13)
- GEODATABASE_FILE_6: GEODATABASE_FILE to $(DestDataset_GEODATABASE_FILE_19)
- GEODATABASE_FILE_2: GEODATABASE_FILE to $(DestDataset_GEODATABASE_FILE_17)
- GEODATABASE_FILE_5: GEODATABASE_FILE to $(DestDataset_GEODATABASE_FILE_15)
- GEODATABASE_FILE_4: GEODATABASE_FILE to $(DestDataset_GEODATABASE_FILE_21)
- GEODATABASE_FILE_7: GEODATABASE_FILE to $(DestDataset_GEODATABASE_FILE_12)
- GEODATABASE_FILE_8: GEODATABASE_FILE to $(DestDataset_GEODATABASE_FILE_14)
- GEODATABASE_FILE_9: GEODATABASE_FILE to $(DestDataset_GEODATABASE_FILE_16)
- GEODATABASE_FILE_10: GEODATABASE_FILE to $(DestDataset_GEODATABASE_FILE_18)
- GEODATABASE_FILE_11: GEODATABASE_FILE to $(DestDataset_GEODATABASE_FILE_20)

Bookmark: Spatial input of DGGS
HawkesBay_H3Resolution11 (reader GEODATABASE_SDE_1)
    attributes: OBJECTID integer, GRID_ID char(17), SHAPE.STArea() double, SHAPE.STLength() double
    -> AttributeKeeper
AttributeKeeper
    CREATE_BULK_MODE_FEATURES = NO
    KEEP_ATTRS = GRID_ID
    -> Reprojector_6
Reprojector_6
    DEST = EPSG:2193
    INTERPOLATION_TYPE = NearestNeighbor
    RASTER_CELL_SIZE = PreserveCells
    RASTER_TOLERANCE = 0.0
    REPROJECTED -> Clipper [CANDIDATE]
HawkesBay_Regional_Boundary_2025 (reader GEODATABASE_SDE_2)
    attributes: OBJECTID integer, REGC_V1_00 char(2), REGC_V1_00_NAME char(254), REGC_V1_00_NAME_ASCII char(200), LAND_AREA_SQ_KM double, SHAPE.STArea() double, SHAPE.STLength() double
    -> Clipper [CLIPPER]
Clipper
    ADD_NODATA = YES
    BOUNDARY_CASES = INSIDE
    CLEANING_TOLERANCE_LOOKUP = AUTO
    CLIPPED_ATTR = _clipped
    CLIPPERS_FIRST = NO
    GENERATE_LIST = NO
    INVALID_PARTS_HANDLING = REJECT_WHOLE
    MISSING_M_MODE_LOOKUP = LINEAR
    MISSING_Z_MODE_LOOKUP = PLANAR
    MULTIPLE_CLIPPERS = YES
    M_VAL_SOURCE = CANDIDATE
    OVERLAPPING_CLIPPERS = CLIP_OUTSIDE
    PRESERVE_RASTER_EXTENTS = NO
    RASTER_CELL_MODE = CENTER
    Z_VAL_SOURCE = CANDIDATE
    CLEANING_TOLERANCE = Automatic
    MISSING_M_MODE = Linear Interpolation
    MISSING_Z_MODE = Planar Interpolation
    INSIDE -> FeatureMerger [REQUESTOR]
    INSIDE -> FeatureMerger_3 [REQUESTOR]

Bookmark: Crops
Note: CSV: CropSuitabilityClassified_All
CSV (reader CSV2_1)
    attributes: GRID_ID varchar(15), LandUseName varchar(72), LandUseGroup varchar(29), MeanAnnualRainfall uint32, MeanSlope real64, SMU varchar(26), SiblingTopsoilStonesCode real32, PAWmm real32, RootDepthRange varchar(10), DrainageClass varchar(23), FrostDays_MAM real64, FrostDays_SON real64, GrowingDegreeDays real64, Salinity real32, PH_MID real64, HeatStress_DJF real64, MeanTemp_SON real64, MinTemp_SON real64, MaxTemp_SON real64, MaxTemp_DJF real64, HarvestRainfall_DJF real64, DrainageScore real32, RootDepth_cm real32, MaizeGrain_ANR_score real32, MaizeGrain_ART_score real32, MaizeGrain_DRC_score real32, MaizeGrain_ECS_score real32, MaizeGrain_FFB_score real32, MaizeGrain_FFH_score real32, MaizeGrain_GDD_score real32,
      MaizeGrain_PRD_score real32, MaizeGrain_PWC_score real32, MaizeGrain_SLP_score real32, MaizeGrain_STN_score real32, MaizeGrain_MeanScore real32, MaizeGrain_FinalClass varchar(17), MaizeGrain_WorstScore real32, MaizeGrain_LimitingFactor varchar(110), MaizeGrain_LimitingClass varchar(17), MaizeGrain_HardExcluded varchar(5), MaizeGrain_HardLimitingFactor varchar(13), MaizeGrain_MissingData varchar(47), Citrus_ANR_score real32, Citrus_ART_score real32, Citrus_DRC_score real32, Citrus_ECS_score real32, Citrus_HFL_score real32, Citrus_MET_score real32, Citrus_MNT_score real32, Citrus_MXT_score real32, Citrus_PHH_score real32, Citrus_PRD_score real32, Citrus_PWC_score real32, Citrus_SLP_score real32, Citrus_STN_score real32, Citrus_MeanScore real32, Citrus_FinalClass varchar(17), Citrus_WorstScore real32, Citrus_LimitingFactor varchar(197), Citrus_LimitingClass varchar(17),
      Citrus_HardExcluded varchar(5), Citrus_HardLimitingFactor varchar(15), Citrus_MissingData varchar(54), Onions_ANR_score real32, Onions_ART_score real32, Onions_DRC_score real32, Onions_ECS_score real32, Onions_FFB_score real32, Onions_HFO_score real32, Onions_PHH_score real32, Onions_PRD_score real32, Onions_PWC_score real32, Onions_RAH_score real32, Onions_SLP_score real32, Onions_STN_score real32, Onions_MeanScore real32, Onions_FinalClass varchar(17), Onions_WorstScore real32, Onions_LimitingFactor varchar(97), Onions_LimitingClass varchar(17), Onions_HardExcluded varchar(5), Onions_HardLimitingFactor varchar(24), Onions_MissingData varchar(47)
    -> FeatureMerger [SUPPLIER]
Note: Add geometry
FeatureMerger
    ATTR_ACCUM_MODE = Merge Supplier
    ATTR_CONFLICT_RES_LOOKUP = REQUESTOR_IF_CONFLICT
    IGNORE_NULLS = No
    JOIN_KEYS = @Value(GRID_ID) @Value(GRID_ID) AUTO
    MERGE_TYPE_VAL = ATTRIBUTES
    PROCESS_DUPS = NO
    REJECT_NULL_MISSING_KEYS = No
    SUPPLIERS_FIRST = No
    ATTR_CONFLICT_RES = Use Requestor
    MERGE_TYPE = Attributes Only
    MERGED -> AttributeManager
AttributeManager
    ATTR_TABLE = SET_TO MaizeGrain_FinalClass (varchar(17)) = FME_CONDITIONAL:DEFAULT_VALUE'_FME_NO_OP_'BOOL_OP;OR;COMPOSITE_TEST;1 OR 2 OR 3 OR 4 OR 5;TEST @Value(LandUseGroup) = Commercial;TEST @Value(LandUseGroup) = Public;TEST @Value(LandUseGroup) = Industrial;TEST @Value(LandUseGroup) = Residential;TEST @Value(LandUseGroup) = Water'Indeterminate'FME_NUM_CONDITIONS2___
    -> DateTimeStamper_2
DateTimeStamper_2
    DATETIME_ATTR = _timestamp
    INCLUDE_FRAC_SECONDS = NO
    SCOPE = translation
    STAMP_TYPE = date
    TIMEZONE = utc
    -> FinalClass_Maize (writer GEODATABASE_FILE_1)
    -> AttributeKeeper_2
    -> AttributeKeeper_3
    -> AttributeKeeper_4
AttributeKeeper_2
    CREATE_BULK_MODE_FEATURES = NO
    KEEP_ATTRS = MaizeGrain_FinalClass,_timestamp
    -> Dissolver_7
Dissolver_7
    ACCUM_INPUT_ATTRS_LOOKUP = One
    CLEANING_TOLERANCE_LOOKUP = AUTO
    CONNECT_Z_MODE_LOOKUP = FIRST_WINS
    DEAGGREGATE_INPUT = Yes
    GROUP_BY = MaizeGrain_FinalClass
    ACCUM_INPUT_ATTRS = Use Attributes From One Feature
    CLEANING_TOLERANCE = Automatic
    CONNECT_Z_MODE = First Wins
    AREA -> FinalClass_Crops_Dissolved_Maize (writer GEODATABASE_FILE_6)
AttributeKeeper_3
    CREATE_BULK_MODE_FEATURES = NO
    KEEP_ATTRS = Citrus_FinalClass,_timestamp
    -> Dissolver_8
Dissolver_8
    ACCUM_INPUT_ATTRS_LOOKUP = One
    CLEANING_TOLERANCE_LOOKUP = AUTO
    CONNECT_Z_MODE_LOOKUP = FIRST_WINS
    DEAGGREGATE_INPUT = Yes
    GROUP_BY = Citrus_FinalClass
    ACCUM_INPUT_ATTRS = Use Attributes From One Feature
    CLEANING_TOLERANCE = Automatic
    CONNECT_Z_MODE = First Wins
    AREA -> FinalClass_Crops_Dissolved_Onions (writer GEODATABASE_FILE_5)
AttributeKeeper_4
    CREATE_BULK_MODE_FEATURES = NO
    KEEP_ATTRS = Onions_FinalClass,_timestamp
    -> Dissolver_9
Dissolver_9
    ACCUM_INPUT_ATTRS_LOOKUP = One
    CLEANING_TOLERANCE_LOOKUP = AUTO
    CONNECT_Z_MODE_LOOKUP = FIRST_WINS
    DEAGGREGATE_INPUT = Yes
    GROUP_BY = Onions_FinalClass
    ACCUM_INPUT_ATTRS = Use Attributes From One Feature
    CLEANING_TOLERANCE = Automatic
    CONNECT_Z_MODE = First Wins
    AREA -> FinalClass_Crops_Dissolved_Onions (writer GEODATABASE_FILE_2)

Bookmark: Outputs
FinalClass_Maize (writer GEODATABASE_FILE_1)
    attributes: GRID_ID char(17), _clipped char(3), LandUseName char(72), LandUseGroup char(29), MeanAnnualRainfall double, MeanSlope double, SMU char(26), SiblingTopsoilStonesCode float, PAWmm float, RootDepthRange char(10), DrainageClass char(23), FrostDays_MAM double, FrostDays_SON double, GrowingDegreeDays double, Salinity float, PH_MID double, HeatStress_DJF double, MeanTemp_SON double, MinTemp_SON double, MaxTemp_SON double, MaxTemp_DJF double, HarvestRainfall_DJF double, MaizeGrain_ANR_score float, MaizeGrain_ART_score float, MaizeGrain_SLP_score float, MaizeGrain_PRD_score float, MaizeGrain_DRC_score float, MaizeGrain_PWC_score float, MaizeGrain_STN_score float, MaizeGrain_FFH_score float,
      MaizeGrain_FFB_score float, MaizeGrain_GDD_score float, MaizeGrain_ECS_score float, MaizeGrain_MeanScore float, MaizeGrain_FinalClass char(17), MaizeGrain_WorstScore float, MaizeGrain_LimitingFactor char(110), MaizeGrain_LimitingClass char(17), MaizeGrain_HardLimitingFactor char(13), MaizeGrain_HardExcluded char(5), DrainageScore float, RootDepth_cm float, MaizeGrain_MissingData char(47), Citrus_ANR_score float, Citrus_ART_score float, Citrus_DRC_score float, Citrus_ECS_score float, Citrus_HFL_score float, Citrus_MET_score float, Citrus_MNT_score float, Citrus_MXT_score float, Citrus_PHH_score float, Citrus_PRD_score float, Citrus_PWC_score float, Citrus_SLP_score float, Citrus_STN_score float, Citrus_MeanScore float, Citrus_FinalClass char(17), Citrus_WorstScore float, Citrus_LimitingFactor char(197),
      Citrus_LimitingClass char(17), Citrus_HardExcluded char(5), Citrus_HardLimitingFactor char(15), Citrus_MissingData char(54), Onions_ANR_score float, Onions_ART_score float, Onions_DRC_score float, Onions_ECS_score float, Onions_FFB_score float, Onions_HFO_score float, Onions_PHH_score float, Onions_PRD_score float, Onions_PWC_score float, Onions_RAH_score float, Onions_SLP_score float, Onions_STN_score float, Onions_MeanScore float, Onions_FinalClass char(17), Onions_WorstScore float, Onions_LimitingFactor char(97), Onions_LimitingClass char(17), Onions_HardExcluded char(5), Onions_HardLimitingFactor char(24), Onions_MissingData char(47), _timestamp date_only
FinalClass_Crops_Dissolved_Maize (writer GEODATABASE_FILE_6)
    attributes: MaizeGrain_FinalClass char(17), _timestamp date_only
FinalClass_Crops_Dissolved_Onions (writer GEODATABASE_FILE_5)
    attributes: Citrus_FinalClass char(17), _timestamp date_only
FinalClass_Crops_Dissolved_Onions (writer GEODATABASE_FILE_2)
    attributes: Onions_FinalClass char(17), _timestamp date_only

Bookmark: RTRP
Note: RTRP_TreeSpecies_H3Res11
CSV (reader CSV2_3)
    attributes: GRID_ID varchar(15), PRad real64, CLus real64, EGenx real64, Manuka real64, Redwoodx real64, Totarax real64
    -> FeatureMerger_2 [REQUESTOR]
Note: LUDB_H3
CSV (reader CSV2_2)
    attributes: GRID_ID varchar(15), LandUseNam varchar(72), LandUseGro varchar(29)
    -> AttributeManager_3
AttributeManager_3
    ATTR_TABLE:
      RENAME_SET_VALUE LandUseNam > LandUseName (varchar(72))
      RENAME_SET_VALUE LandUseGro > LandUseGroup (varchar(29))
    -> FeatureMerger_2 [SUPPLIER]
FeatureMerger_2
    ATTR_ACCUM_MODE = Merge Supplier
    ATTR_CONFLICT_RES_LOOKUP = REQUESTOR_IF_CONFLICT
    IGNORE_NULLS = No
    JOIN_KEYS = @Value(GRID_ID) @Value(GRID_ID) AUTO
    MERGE_TYPE_VAL = ATTRIBUTES
    PROCESS_DUPS = NO
    REJECT_NULL_MISSING_KEYS = No
    SUPPLIERS_FIRST = No
    ATTR_CONFLICT_RES = Use Requestor
    MERGE_TYPE = Attributes Only
    MERGED -> AttributeCreator
Note: Suitability classification
AttributeCreator
    ATTR_TABLE:
      SET_TO TreeSuitability_CLus (varchar(200)) = FME_CONDITIONAL:DEFAULT_VALUE'_FME_NO_OP_'BOOL_OP;OR;COMPOSITE_TEST;1;TEST @Value(CLus) > 0.75'Well Suited'BOOL_OP;AND;COMPOSITE_TEST;1 AND 2;TEST @Value(CLus) <= 0.75;TEST @Value(CLus) > 0.5'Suited'BOOL_OP;AND;COMPOSITE_TEST;1 AND 2;TEST @Value(CLus) <= 0.5;TEST @Value(CLus) > 0.25'Moderately Suited'BOOL_OP;OR;COMPOSITE_TEST;1;TEST @Value(CLus) <= 0.25'Unsuitable'FME_NUM_CONDITIONS5___
      SET_TO TreeSuitability_EGenx (varchar(200)) = FME_CONDITIONAL:DEFAULT_VALUE'_FME_NO_OP_'BOOL_OP;OR;COMPOSITE_TEST;1;TEST @Value(EGenx) > 0.75'Well Suited'BOOL_OP;AND;COMPOSITE_TEST;1 AND 2;TEST @Value(EGenx) <= 0.75;TEST @Value(EGenx) > 0.5'Suited'BOOL_OP;AND;COMPOSITE_TEST;1 AND 2;TEST @Value(EGenx) <= 0.5;TEST @Value(EGenx) > 0.25'Moderately Suited'BOOL_OP;OR;COMPOSITE_TEST;1;TEST @Value(EGenx) <= 0.25'Unsuitable'FME_NUM_CONDITIONS5___
      SET_TO TreeSuitability_Manuka (varchar(200)) = FME_CONDITIONAL:DEFAULT_VALUE'_FME_NO_OP_'BOOL_OP;OR;COMPOSITE_TEST;1;TEST @Value(Manuka) > 0.75'Well Suited'BOOL_OP;AND;COMPOSITE_TEST;1 AND 2;TEST @Value(Manuka) <= 0.75;TEST @Value(Manuka) > 0.5'Suited'BOOL_OP;AND;COMPOSITE_TEST;1 AND 2;TEST @Value(Manuka) <= 0.5;TEST @Value(Manuka) > 0.25'Moderately Suited'BOOL_OP;OR;COMPOSITE_TEST;1;TEST @Value(Manuka) <= 0.25'Unsuitable'FME_NUM_CONDITIONS5___
      SET_TO TreeSuitability_PRad (varchar(200)) = FME_CONDITIONAL:DEFAULT_VALUE'_FME_NO_OP_'BOOL_OP;OR;COMPOSITE_TEST;1;TEST @Value(PRad) > 0.75'Well Suited'BOOL_OP;AND;COMPOSITE_TEST;1 AND 2;TEST @Value(PRad) <= 0.75;TEST @Value(PRad) > 0.5'Suited'BOOL_OP;AND;COMPOSITE_TEST;1 AND 2;TEST @Value(PRad) <= 0.5;TEST @Value(PRad) > 0.25'Moderately Suited'BOOL_OP;OR;COMPOSITE_TEST;1;TEST @Value(PRad) <= 0.25'Unsuitable'FME_NUM_CONDITIONS5___
      SET_TO TreeSuitability_Redwoodx (varchar(200)) = FME_CONDITIONAL:DEFAULT_VALUE'_FME_NO_OP_'BOOL_OP;OR;COMPOSITE_TEST;1;TEST @Value(Redwoodx) > 0.75'Well Suited'BOOL_OP;AND;COMPOSITE_TEST;1 AND 2;TEST @Value(Redwoodx) <= 0.75;TEST @Value(Redwoodx) > 0.5'Suited'BOOL_OP;AND;COMPOSITE_TEST;1 AND 2;TEST @Value(Redwoodx) <= 0.5;TEST @Value(Redwoodx) > 0.25'Moderately Suited'BOOL_OP;OR;COMPOSITE_TEST;1;TEST @Value(Redwoodx) <= 0.25'Unsuitable'FME_NUM_CONDITIONS5___
      SET_TO TreeSuitability_Totarax (varchar(200)) = FME_CONDITIONAL:DEFAULT_VALUE'_FME_NO_OP_'BOOL_OP;OR;COMPOSITE_TEST;1;TEST @Value(Totarax) > 0.75'Well Suited'BOOL_OP;AND;COMPOSITE_TEST;1 AND 2;TEST @Value(Totarax) <= 0.75;TEST @Value(Totarax) > 0.5'Suited'BOOL_OP;AND;COMPOSITE_TEST;1 AND 2;TEST @Value(Totarax) <= 0.5;TEST @Value(Totarax) > 0.25'Moderately Suited'BOOL_OP;OR;COMPOSITE_TEST;1;TEST @Value(Totarax) <= 0.25'Unsuitable'FME_NUM_CONDITIONS5___
    -> AttributeManager_2
AttributeManager_2
    ATTR_TABLE:
      SET_TO TreeSuitability_CLus (varchar(200)) = FME_CONDITIONAL:DEFAULT_VALUE'_FME_NO_OP_'BOOL_OP;OR;COMPOSITE_TEST;1 OR 2 OR 3 OR 4 OR 5;TEST @Value(LandUseGroup) = Commercial;TEST @Value(LandUseGroup) = Public;TEST @Value(LandUseGroup) = Industrial;TEST @Value(LandUseGroup) = Residential;TEST @Value(LandUseGroup) = Water'Indeterminate'FME_NUM_CONDITIONS2___
      SET_TO TreeSuitability_EGenx (varchar(200)) = FME_CONDITIONAL:DEFAULT_VALUE'_FME_NO_OP_'BOOL_OP;OR;COMPOSITE_TEST;1 OR 2 OR 3 OR 4 OR 5;TEST @Value(LandUseGroup) = Commercial;TEST @Value(LandUseGroup) = Public;TEST @Value(LandUseGroup) = Industrial;TEST @Value(LandUseGroup) = Residential;TEST @Value(LandUseGroup) = Water'Indeterminate'FME_NUM_CONDITIONS2___
      SET_TO TreeSuitability_Manuka (varchar(200)) = FME_CONDITIONAL:DEFAULT_VALUE'_FME_NO_OP_'BOOL_OP;OR;COMPOSITE_TEST;1 OR 2 OR 3 OR 4 OR 5;TEST @Value(LandUseGroup) = Commercial;TEST @Value(LandUseGroup) = Public;TEST @Value(LandUseGroup) = Industrial;TEST @Value(LandUseGroup) = Residential;TEST @Value(LandUseGroup) = Water'Indeterminate'FME_NUM_CONDITIONS2___
      SET_TO TreeSuitability_PRad (varchar(200)) = FME_CONDITIONAL:DEFAULT_VALUE'_FME_NO_OP_'BOOL_OP;OR;COMPOSITE_TEST;1 OR 2 OR 3 OR 4 OR 5;TEST @Value(LandUseGroup) = Commercial;TEST @Value(LandUseGroup) = Public;TEST @Value(LandUseGroup) = Industrial;TEST @Value(LandUseGroup) = Residential;TEST @Value(LandUseGroup) = Water'Indeterminate'FME_NUM_CONDITIONS2___
      SET_TO TreeSuitability_Redwoodx (varchar(200)) = FME_CONDITIONAL:DEFAULT_VALUE'_FME_NO_OP_'BOOL_OP;OR;COMPOSITE_TEST;1 OR 2 OR 3 OR 4 OR 5;TEST @Value(LandUseGroup) = Commercial;TEST @Value(LandUseGroup) = Public;TEST @Value(LandUseGroup) = Industrial;TEST @Value(LandUseGroup) = Residential;TEST @Value(LandUseGroup) = Water'Indeterminate'FME_NUM_CONDITIONS2___
      SET_TO TreeSuitability_Totarax (varchar(200)) = FME_CONDITIONAL:DEFAULT_VALUE'_FME_NO_OP_'BOOL_OP;OR;COMPOSITE_TEST;1 OR 2 OR 3 OR 4 OR 5;TEST @Value(LandUseGroup) = Commercial;TEST @Value(LandUseGroup) = Public;TEST @Value(LandUseGroup) = Industrial;TEST @Value(LandUseGroup) = Residential;TEST @Value(LandUseGroup) = Water'Indeterminate'FME_NUM_CONDITIONS2___
    -> FeatureMerger_3 [SUPPLIER]
Note: Add geometry
FeatureMerger_3
    ATTR_ACCUM_MODE = Merge Supplier
    ATTR_CONFLICT_RES_LOOKUP = REQUESTOR_IF_CONFLICT
    IGNORE_NULLS = No
    JOIN_KEYS = @Value(GRID_ID) @Value(GRID_ID) AUTO
    MERGE_TYPE_VAL = GEOM_AND_ATTRS
    PROCESS_DUPS = NO
    REJECT_NULL_MISSING_KEYS = No
    SUPPLIERS_FIRST = No
    ATTR_CONFLICT_RES = Use Requestor
    MERGE_TYPE = Attributes and Geometry
    MERGED -> SpatialRelator [Requestor]
HawkesBay_Catchments_LCDBv06 (reader GEODATABASE_SDE_3)
    attributes: OBJECTID integer, Name_2023 char(50), Name_2018 char(50), Name_2012 char(50), Name_2008 char(50), Name_2001 char(50), Name_1996 char(50), Class_2023 integer, Class_2018 integer, Class_2012 integer, Class_2008 integer, Class_2001 integer, Class_1996 integer, Wetland_23 char(3), Wetland_18 char(3), Wetland_12 char(3), Wetland_08 char(3), Wetland_01 char(3), Wetland_96 char(3), Onshore_23 char(4), Onshore_18 char(4), Onshore_12 char(4), Onshore_08 char(4), Onshore_01 char(4), Onshore_96 char(4), EditAuthor char(20), EditDate date, LCDB_UID char(16), SHAPE.STArea() double, SHAPE.STLength() double
    -> Tester
Tester
    BOOL_OP = OR
    TEST_CLAUSE:
      TEST @Value(Name_2023) = Built-up Area (settlement)
      TEST @Value(Name_2023) = Urban Parkland/Open Space
    TEST_MODE = TEST
    PASSED -> SpatialRelator [Supplier]
Note: Reclass urban areas that were missed
SpatialRelator
    AGGREGATE_HANDLING = Yes
    CALC_CARD = No
    CURVE_BOUNDARY_RULE_PARAM = Default Rule
    PREDICATES = INTERSECTS
    SUCCESS_ATTR = _related_suppliers
    -> AttributeManager_4
Note: Add Indeterminate class
AttributeManager_4
    ATTR_TABLE:
      REMOVE _clipped (char(3))
      SET_TO TreeSuitability_CLus (varchar(200)) = FME_CONDITIONAL:DEFAULT_VALUE'_FME_NO_OP_'BOOL_OP;OR;COMPOSITE_TEST;1;TEST @Value(_related_suppliers) > 0'Indeterminate'FME_NUM_CONDITIONS2___
      SET_TO TreeSuitability_EGenx (varchar(200)) = FME_CONDITIONAL:DEFAULT_VALUE'_FME_NO_OP_'BOOL_OP;OR;COMPOSITE_TEST;1;TEST @Value(_related_suppliers) > 0'Indeterminate'FME_NUM_CONDITIONS2___
      SET_TO TreeSuitability_Manuka (varchar(200)) = FME_CONDITIONAL:DEFAULT_VALUE'_FME_NO_OP_'BOOL_OP;OR;COMPOSITE_TEST;1;TEST @Value(_related_suppliers) > 0'Indeterminate'FME_NUM_CONDITIONS2___
      SET_TO TreeSuitability_PRad (varchar(200)) = FME_CONDITIONAL:DEFAULT_VALUE'_FME_NO_OP_'BOOL_OP;OR;COMPOSITE_TEST;1;TEST @Value(_related_suppliers) > 0'Indeterminate'FME_NUM_CONDITIONS2___
      SET_TO TreeSuitability_Redwoodx (varchar(200)) = FME_CONDITIONAL:DEFAULT_VALUE'_FME_NO_OP_'BOOL_OP;OR;COMPOSITE_TEST;1;TEST @Value(_related_suppliers) > 0'Indeterminate'FME_NUM_CONDITIONS2___
      SET_TO TreeSuitability_Totarax (varchar(200)) = FME_CONDITIONAL:DEFAULT_VALUE'_FME_NO_OP_'BOOL_OP;OR;COMPOSITE_TEST;1;TEST @Value(_related_suppliers) > 0'Indeterminate'FME_NUM_CONDITIONS2___
      REMOVE _related_suppliers (uint32)
    -> SpatialRelator_2 [Requestor]
HawkesBay_LocalAuthorityBoundaries_2025 (reader GEODATABASE_SDE_4)
    attributes: OBJECTID integer, TA_V1_00 char(10), TA_V1_00_NAME char(250), TA_V1_00_NAME_ASCII char(250), LAND_AREA_SQ_KM double, SHAPE.STArea() double, SHAPE.STLength() double
    -> SpatialRelator_2 [Supplier]
SpatialRelator_2
    AGGREGATE_HANDLING = Yes
    CALC_CARD = No
    CURVE_BOUNDARY_RULE_PARAM = Default Rule
    LIST_NAME = _relationships
    PREDICATES = INTERSECTS
    SUCCESS_ATTR = _related_suppliers
    -> Tester_2
Note: Remove coastal areas
Tester_2
    BOOL_OP = OR
    TEST_CLAUSE = TEST @Value(_related_suppliers) = 1
    TEST_MODE = TEST
    PASSED -> DateTimeStamper
DateTimeStamper
    DATETIME_ATTR = _timestamp
    INCLUDE_FRAC_SECONDS = NO
    SCOPE = translation
    STAMP_TYPE = date
    TIMEZONE = utc
    -> AttributeManager_11
    -> AttributeManager_5
    -> AttributeManager_6
    -> AttributeManager_7
    -> AttributeManager_8
    -> AttributeManager_9
    -> AttributeManager_10
AttributeManager_11
    ATTR_TABLE:
      REMOVE _relationships{}.de9im (buffer)
      REMOVE _relationships{}.pass{} (buffer)
      REMOVE _related_suppliers (uint32)
    -> FinalClass_Trees (writer GEODATABASE_FILE_3)
FinalClass_Trees (writer GEODATABASE_FILE_3)
    attributes: GRID_ID char(17), TreeSuitability_CLus char(200), TreeSuitability_EGenx char(200), TreeSuitability_Manuka char(200), TreeSuitability_PRad char(200), TreeSuitability_Redwoodx char(200), TreeSuitability_Totarax char(200), PRad double, CLus double, EGenx double, Manuka double, Redwoodx double, Totarax double, LandUseName char(72), LandUseGroup char(29), _timestamp date_only
Note: C Lus
AttributeManager_5
    ATTR_TABLE:
      REMOVE GRID_ID (varchar(17))
      REMOVE TreeSuitability_EGenx (varchar(200))
      REMOVE TreeSuitability_Manuka (varchar(200))
      REMOVE TreeSuitability_PRad (varchar(200))
      REMOVE TreeSuitability_Redwoodx (varchar(200))
      REMOVE TreeSuitability_Totarax (varchar(200))
      REMOVE PRad (real64)
      REMOVE CLus (real64)
      REMOVE EGenx (real64)
      REMOVE Manuka (real64)
      REMOVE Redwoodx (real64)
      REMOVE Totarax (real64)
      REMOVE LandUseName (varchar(72))
      REMOVE LandUseGroup (varchar(29))
      REMOVE _relationships{}.de9im (buffer)
      REMOVE _relationships{}.pass{} (buffer)
      REMOVE _related_suppliers (uint32)
    -> Dissolver
Dissolver
    ACCUM_INPUT_ATTRS_LOOKUP = One
    CLEANING_TOLERANCE_LOOKUP = AUTO
    CONNECT_Z_MODE_LOOKUP = FIRST_WINS
    DEAGGREGATE_INPUT = Yes
    GROUP_BY = TreeSuitability_CLus
    ACCUM_INPUT_ATTRS = Use Attributes From One Feature
    CLEANING_TOLERANCE = Automatic
    CONNECT_Z_MODE = First Wins
    AREA -> FinalClass_Trees_CLus (writer GEODATABASE_FILE_4)
FinalClass_Trees_CLus (writer GEODATABASE_FILE_4)
    attributes: TreeSuitability_CLus char(200), _timestamp date_only
Note: Euc Gen
AttributeManager_6
    ATTR_TABLE:
      REMOVE TreeSuitability_CLus (varchar(200))
      REMOVE TreeSuitability_Manuka (varchar(200))
      REMOVE TreeSuitability_PRad (varchar(200))
      REMOVE TreeSuitability_Redwoodx (varchar(200))
      REMOVE TreeSuitability_Totarax (varchar(200))
      REMOVE PRad (real64)
      REMOVE CLus (real64)
      REMOVE EGenx (real64)
      REMOVE Manuka (real64)
      REMOVE Redwoodx (real64)
      REMOVE Totarax (real64)
      REMOVE LandUseName (varchar(72))
      REMOVE LandUseGroup (varchar(29))
      REMOVE _relationships{}.de9im (buffer)
      REMOVE _relationships{}.pass{} (buffer)
      REMOVE _related_suppliers (uint32)
    -> Dissolver_2
Dissolver_2
    ACCUM_INPUT_ATTRS_LOOKUP = One
    CLEANING_TOLERANCE_LOOKUP = AUTO
    CONNECT_Z_MODE_LOOKUP = FIRST_WINS
    DEAGGREGATE_INPUT = Yes
    GROUP_BY = TreeSuitability_EGenx
    ACCUM_INPUT_ATTRS = Use Attributes From One Feature
    CLEANING_TOLERANCE = Automatic
    CONNECT_Z_MODE = First Wins
    AREA -> FinalClass_Trees_CLus (writer GEODATABASE_FILE_7)
FinalClass_Trees_CLus (writer GEODATABASE_FILE_7)
    attributes: TreeSuitability_EGenx char(200), GRID_ID char(17), _timestamp date_only
Note: Manuka
AttributeManager_7
    ATTR_TABLE:
      REMOVE GRID_ID (varchar(17))
      REMOVE TreeSuitability_CLus (varchar(200))
      REMOVE TreeSuitability_EGenx (varchar(200))
      REMOVE TreeSuitability_PRad (varchar(200))
      REMOVE TreeSuitability_Redwoodx (varchar(200))
      REMOVE TreeSuitability_Totarax (varchar(200))
      REMOVE PRad (real64)
      REMOVE CLus (real64)
      REMOVE EGenx (real64)
      REMOVE Manuka (real64)
      REMOVE Redwoodx (real64)
      REMOVE Totarax (real64)
      REMOVE LandUseName (varchar(72))
      REMOVE LandUseGroup (varchar(29))
      REMOVE _relationships{}.de9im (buffer)
      REMOVE _relationships{}.pass{} (buffer)
      REMOVE _related_suppliers (uint32)
    -> Dissolver_3
Dissolver_3
    ACCUM_INPUT_ATTRS_LOOKUP = One
    CLEANING_TOLERANCE_LOOKUP = AUTO
    CONNECT_Z_MODE_LOOKUP = FIRST_WINS
    DEAGGREGATE_INPUT = Yes
    GROUP_BY = TreeSuitability_Manuka
    ACCUM_INPUT_ATTRS = Use Attributes From One Feature
    CLEANING_TOLERANCE = Automatic
    CONNECT_Z_MODE = First Wins
    AREA -> FinalClass_Trees_Manuka (writer GEODATABASE_FILE_8)
FinalClass_Trees_Manuka (writer GEODATABASE_FILE_8)
    attributes: TreeSuitability_Manuka char(200), _timestamp date_only
Note: P Rad
AttributeManager_8
    ATTR_TABLE:
      REMOVE GRID_ID (varchar(17))
      REMOVE TreeSuitability_CLus (varchar(200))
      REMOVE TreeSuitability_EGenx (varchar(200))
      REMOVE TreeSuitability_Manuka (varchar(200))
      REMOVE TreeSuitability_Redwoodx (varchar(200))
      REMOVE TreeSuitability_Totarax (varchar(200))
      REMOVE PRad (real64)
      REMOVE CLus (real64)
      REMOVE EGenx (real64)
      REMOVE Manuka (real64)
      REMOVE Redwoodx (real64)
      REMOVE Totarax (real64)
      REMOVE LandUseName (varchar(72))
      REMOVE LandUseGroup (varchar(29))
      REMOVE _relationships{}.de9im (buffer)
      REMOVE _relationships{}.pass{} (buffer)
      REMOVE _related_suppliers (uint32)
    -> Dissolver_4
Dissolver_4
    ACCUM_INPUT_ATTRS_LOOKUP = One
    CLEANING_TOLERANCE_LOOKUP = AUTO
    CONNECT_Z_MODE_LOOKUP = FIRST_WINS
    DEAGGREGATE_INPUT = Yes
    GROUP_BY = TreeSuitability_PRad
    ACCUM_INPUT_ATTRS = Use Attributes From One Feature
    CLEANING_TOLERANCE = Automatic
    CONNECT_Z_MODE = First Wins
    AREA -> FinalClass_Trees_PRad (writer GEODATABASE_FILE_9)
FinalClass_Trees_PRad (writer GEODATABASE_FILE_9)
    attributes: TreeSuitability_PRad char(200), _timestamp date_only
Note: Redwood
AttributeManager_9
    ATTR_TABLE:
      REMOVE GRID_ID (varchar(17))
      REMOVE TreeSuitability_CLus (varchar(200))
      REMOVE TreeSuitability_EGenx (varchar(200))
      REMOVE TreeSuitability_Manuka (varchar(200))
      REMOVE TreeSuitability_PRad (varchar(200))
      REMOVE TreeSuitability_Totarax (varchar(200))
      REMOVE PRad (real64)
      REMOVE CLus (real64)
      REMOVE EGenx (real64)
      REMOVE Manuka (real64)
      REMOVE Redwoodx (real64)
      REMOVE Totarax (real64)
      REMOVE LandUseName (varchar(72))
      REMOVE LandUseGroup (varchar(29))
      REMOVE _relationships{}.de9im (buffer)
      REMOVE _relationships{}.pass{} (buffer)
      REMOVE _related_suppliers (uint32)
    -> Dissolver_5
Dissolver_5
    ACCUM_INPUT_ATTRS_LOOKUP = One
    CLEANING_TOLERANCE_LOOKUP = AUTO
    CONNECT_Z_MODE_LOOKUP = FIRST_WINS
    DEAGGREGATE_INPUT = Yes
    GROUP_BY = TreeSuitability_Redwoodx
    ACCUM_INPUT_ATTRS = Use Attributes From One Feature
    CLEANING_TOLERANCE = Automatic
    CONNECT_Z_MODE = First Wins
    AREA -> FinalClass_Trees_Redwood (writer GEODATABASE_FILE_10)
FinalClass_Trees_Redwood (writer GEODATABASE_FILE_10)
    attributes: TreeSuitability_Redwoodx char(200), _timestamp date_only
Note: Totara
AttributeManager_10
    ATTR_TABLE:
      REMOVE GRID_ID (varchar(17))
      REMOVE TreeSuitability_CLus (varchar(200))
      REMOVE TreeSuitability_EGenx (varchar(200))
      REMOVE TreeSuitability_Manuka (varchar(200))
      REMOVE TreeSuitability_PRad (varchar(200))
      REMOVE TreeSuitability_Redwoodx (varchar(200))
      REMOVE PRad (real64)
      REMOVE CLus (real64)
      REMOVE EGenx (real64)
      REMOVE Manuka (real64)
      REMOVE Redwoodx (real64)
      REMOVE Totarax (real64)
      REMOVE LandUseName (varchar(72))
      REMOVE LandUseGroup (varchar(29))
      REMOVE _relationships{}.de9im (buffer)
      REMOVE _relationships{}.pass{} (buffer)
      REMOVE _related_suppliers (uint32)
    -> Dissolver_6
Dissolver_6
    ACCUM_INPUT_ATTRS_LOOKUP = One
    CLEANING_TOLERANCE_LOOKUP = AUTO
    CONNECT_Z_MODE_LOOKUP = FIRST_WINS
    DEAGGREGATE_INPUT = Yes
    GROUP_BY = TreeSuitability_Totarax
    ACCUM_INPUT_ATTRS = Use Attributes From One Feature
    CLEANING_TOLERANCE = Automatic
    CONNECT_Z_MODE = First Wins
    AREA -> FinalClass_Trees_Totara (writer GEODATABASE_FILE_11)
FinalClass_Trees_Totara (writer GEODATABASE_FILE_11)
    attributes: TreeSuitability_Totarax char(200), _timestamp date_only
